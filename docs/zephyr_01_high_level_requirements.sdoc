[DOCUMENT]
TITLE: Zephyr High Level Requirements
REQ_PREFIX: ZEP-

[GRAMMAR]
ELEMENTS:
- TAG: REQUIREMENT
  FIELDS:
  - TITLE: UID
    TYPE: String
    REQUIRED: False
  - TITLE: STATUS
    TYPE: String
    REQUIRED: False
  - TITLE: TYPE
    TYPE: String
    REQUIRED: False
  - TITLE: COMPONENT
    TYPE: String
    REQUIRED: False
  - TITLE: TITLE
    TYPE: String
    REQUIRED: False
  - TITLE: STATEMENT
    TYPE: String
    REQUIRED: False
  - TITLE: USER_STORY
    TYPE: String
    REQUIRED: False
  - TITLE: REVIEW_COMMENT
    TYPE: String
    REQUIRED: False
  RELATIONS:
  - TYPE: Parent

[REQUIREMENT]
UID: ZEP-1
STATUS: Draft
TYPE: High Level
COMPONENT: Hardware Architecture Interface
TITLE: Architecture Layer Interface
STATEMENT: >>>
The Zephyr RTOS shall provide a framework to communicate with a set of hardware architectural services.
<<<
USER_STORY: >>>
As a Zephyr RTOS user I want to be able to easily switch my application to a different MCU architecture (x86, ARM Cortex-M/A, RISCV etc.).
<<<

[REQUIREMENT]
UID: ZEP-3
STATUS: Draft
TYPE: High Level
COMPONENT: Hardware Architecture Interface
TITLE: Support multiprocessor management
STATEMENT: >>>
The Zephyr RTOS shall support symmetric multiprocessing on multiple cores.
<<<
USER_STORY: >>>
As a Zephyr RTOS user I want to use Zephyr OS on multi core (SMP-)MCUs/MPUs.
<<<
REVIEW_COMMENT: >>>
From the Docs: No special application code needs to be written to take advantage of this feature
<<<
RELATIONS:
- TYPE: Parent
  VALUE: ZEP-1

[REQUIREMENT]
UID: ZEP-2
STATUS: Draft
TYPE: High Level
COMPONENT: C Library
TITLE: Support Subset of Standard C Library
STATEMENT: >>>
The Zephyr RTOS shall support a subset of the standard C library.
<<<
USER_STORY: >>>
As a Zephyr RTOS user I want to have a selection of standard C library implementations e.g. a full extend and a minimal with a smaller footprint or a particular fast executing implementation.
<<<
REVIEW_COMMENT: >>>
Can we limit the type of C library implementations? Testing might be hell if we do not limit ourselves to the ones defined? Like "minimal libc" and "newlib". Will it make sense to pull minimal Libc into the certification scope?

Clarification: Would prefer to cover the scope part first. Talking about the hooks which apply to each C Library. Open, Close, Diff. Hooks that are OS dependent. C or Library dependent. ref https://github.com/zephyrproject-rtos/zephyr/blob/main/lib/libc/newlib/libc-hooks.c

TBD: The requirement needs refinement.
<<<

[REQUIREMENT]
UID: ZEP-36
STATUS: Draft
TYPE: High Level
COMPONENT: Device Drivers
TITLE: Device Driver Abstraction
STATEMENT: >>>
The Zephyr RTOS shall provide a framework for managing device drivers and peripherals.
<<<
USER_STORY: >>>
As a Zephyr RTOS user I want my application to be portable between different MCU architectures (ARM Cortex-M/A, Intel x86, RISCV etc.) and MCU vendors (STM, NXP, Intel, etc.) without having to change the MCU peripherals access.
<<<
REVIEW_COMMENT: >>>
TBD: Title seems to need refinement. Also, this requirement's user story seems to be identical to that of ZEP-1.
<<<

[REQUIREMENT]
UID: ZEP-37
STATUS: Draft
TYPE: High Level
COMPONENT: Exception and Error Handling
TITLE: Fatal error and exception handling
STATEMENT: >>>
The Zephyr RTOS shall provide a framework for error and exception handling.
<<<
USER_STORY: >>>
As a Zephyr RTOS user I want errors and exceptions to handled and react according to my applications requirements (e.g. reach/establish the applications safety state).
<<<

[REQUIREMENT]
UID: ZEP-38
STATUS: Draft
TYPE: High Level
COMPONENT: File Systems
TITLE: Common File system operation support
STATEMENT: >>>
The Zephyr RTOS shall provide a framework for managing file system access.
<<<
USER_STORY: >>>
As a Zephyr RTOS user I want a posix / c like file system access to store data.
<<<

[REQUIREMENT]
UID: ZEP-39
STATUS: Draft
TYPE: High Level
COMPONENT: Interrupts
TITLE: Interrupt Service Routine
STATEMENT: >>>
The Zephyr RTOS shall provide a framework for interrupt management.
<<<
USER_STORY: >>>
As a Zephyr RTOS user I want interrupts to be handled synchronously in response to a hardware or software interrupt request with a minimum latency, preempting threads and, as far as the hardware allows, lower priority interrupt service routines.
<<<

[REQUIREMENT]
UID: ZEP-40
STATUS: Draft
TYPE: High Level
COMPONENT: Logging
TITLE: Logging
STATEMENT: >>>
The Zephyr RTOS shall provide a framework for logging events.
<<<
USER_STORY: >>>
As a Zephyr RTOS user I want to be able to log application defined events as well as framework exceptions.
<<<
REVIEW_COMMENT: >>>
Nicole: TBD: we need to have logging in the safety scope?
<<<

[REQUIREMENT]
UID: ZEP-41
STATUS: Draft
TYPE: High Level
COMPONENT: Memory Management
TITLE: Memory Management framework
STATEMENT: >>>
The Zephyr RTOS shall support a memory management framework.
<<<
USER_STORY: >>>
As a Zephyr RTOS user I want memory to be allocated and protected to my application threads preventing mistakenly access to foreign memory as far as the hardware allows.
<<<

[REQUIREMENT]
UID: ZEP-42
STATUS: Draft
TYPE: High Level
COMPONENT: Power Management
TITLE: Power Management
STATEMENT: >>>
The Zephyr RTOS shall provide an interface to control hardware power states.
<<<
USER_STORY: >>>
As a Zephyr RTOS user I want to be able to control the power mode of the MCU and its peripherals to take advantage of the hardware features and to be able to implement low power or battery driven long life applications.
<<<

[SECTION]
TITLE: Multi core and SMP

[REQUIREMENT]
UID: ZEP-44
STATUS: Draft
TYPE: High Level
COMPONENT: SMP and Multi core
TITLE: Multiple CPU scheduling
STATEMENT: >>>
The Zephyr RTOS shall support scheduling of threads on multiple hardware CPUs.
<<<
USER_STORY: >>>
As a Zephyr RTOS user I want Zephyr OS to run on MCUs/CPUs with one or more CPU cores.
<<<

[REQUIREMENT]
UID: ZEP-4
STATUS: Draft
TYPE: High Level
COMPONENT: SMP and Multi core
TITLE: Scheduling
STATEMENT: >>>
The Zephyr RTOS shall provide an interface to assign a thread to a specific CPU.
<<<
USER_STORY: >>>
As a Zephyr RTOS user, I want to be able to control which thread will run on which CPU.
<<<

[/SECTION]

[SECTION]
TITLE: Thread Synchronization

[REQUIREMENT]
UID: ZEP-43
STATUS: Draft
TYPE: High Level
COMPONENT: Mutex
TITLE: Mutex
STATEMENT: >>>
The Zephyr RTOS shall provide an interface for managing communication between threads.
<<<
USER_STORY: >>>
As a Zephyr RTOS user I want to able to exchange information between threads in a thread-safe manner guaranteeing data consistence.
<<<

[REQUIREMENT]
UID: ZEP-99
STATUS: Draft
TYPE: High Level
COMPONENT: Semaphore
TITLE: Counting Semaphore
STATEMENT: >>>
The system shall implement a semaphore synchronization primitive for coordinating access to shared resources among multiple threads.
<<<
USER_STORY: >>>
As a software developer threaded with implementing resource management in our real-time operating system (RTOS), I want to integrate a semaphore synchronization primitive to facilitate coordinated access to shared resources among multiple threads.
<<<

[/SECTION]

[SECTION]
TITLE: Threads

[REQUIREMENT]
UID: ZEP-123
STATUS: Draft
TYPE: High Level
COMPONENT: Threads
TITLE: Thread support
STATEMENT: >>>
The Zephyr RTOS shall support threads.
<<<
USER_STORY: >>>
As a Zephyr RTOS user, I want to be able to have support for the kernel objects named threads for processing work.
<<<

[REQUIREMENT]
UID: ZEP-5
STATUS: Draft
TYPE: High Level
COMPONENT: Threads
TITLE: Thread management
STATEMENT: >>>
The Zephyr RTOS shall provide a framework for managing multiple threads of execution.
<<<
USER_STORY: >>>
As a Zephyr RTOS user, I want to be able to manage the execute of multiple threads with different priorities.
<<<
REVIEW_COMMENT: >>>
TBD: Nothing about priorities...
<<<

[REQUIREMENT]
UID: ZEP-122
STATUS: Draft
TYPE: High Level
COMPONENT: Threads
TITLE: Thread priority
STATEMENT: >>>
Threads shall have a priority.
<<<
USER_STORY: >>>
As a Zephyr RTOS user, I want to be able to give my threads different priorities for execution.
<<<

[/SECTION]

[REQUIREMENT]
UID: ZEP-6
STATUS: Draft
TYPE: High Level
COMPONENT: Timers
TITLE: Timers
STATEMENT: >>>
The Zephyr RTOS shall provide a framework for managing time-based events.
<<<
USER_STORY: >>>
As a Zephyr RTOS user, I want to start, suspend, resume and stop timers which shall trigger an event on a set expiration time.
<<<

[REQUIREMENT]
UID: ZEP-7
STATUS: Draft
TYPE: High Level
COMPONENT: Tracing
TITLE: Tracing
STATEMENT: >>>
Zepyhr shall provide a framework mechanism for tracing low level system operations  (NOTE: system calls, interrupts, kernel calls, thread, synchronization, etc.).
<<<
USER_STORY: >>>
As a Zephyr RTOS user, I want to be able to trace different OS operations.
<<<
REVIEW_COMMENT: >>>
TBD: What are low level system operations in this context?
<<<
