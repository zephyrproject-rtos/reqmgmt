[DOCUMENT]
TITLE: Tracing
REQ_PREFIX: ZEP-SRS-10-

[GRAMMAR]
IMPORT_FROM_FILE: software_requirements.sgra

[TEXT]
STATEMENT: >>>
SPDX-License-Identifier: Apache-2.0
<<<

[REQUIREMENT]
UID: ZEP-SRS-10-1
STATUS: Draft
TYPE: Functional
COMPONENT: Tracing
TITLE: Initializing a trace
STATEMENT: >>>
Zephyr shall provide an interface to initialize a trace.
<<<
RELATIONS:
- TYPE: Parent
  VALUE: ZEP-SYRS-19

[REQUIREMENT]
UID: ZEP-SRS-10-2
STATUS: Draft
TYPE: Functional
COMPONENT: Tracing
TITLE: Triggering a trace
STATEMENT: >>>
Zephyr shall provide an interface to trigger a trace.
<<<
RELATIONS:
- TYPE: Parent
  VALUE: ZEP-SYRS-19

[REQUIREMENT]
UID: ZEP-SRS-10-3
STATUS: Draft
TYPE: Functional
COMPONENT: Tracing
TITLE: Dumping trace results
STATEMENT: >>>
Zephyr shall provide an interface to dump results from a trace.
<<<
RELATIONS:
- TYPE: Parent
  VALUE: ZEP-SYRS-19

[REQUIREMENT]
UID: ZEP-SRS-10-4
STATUS: Draft
TYPE: Functional
COMPONENT: Tracing
TITLE: Removing trace data
STATEMENT: >>>
Zephyr shall provide an interface to remove trace data.
<<<
RELATIONS:
- TYPE: Parent
  VALUE: ZEP-SYRS-19

[REQUIREMENT]
UID: ZEP-SRS-10-5
STATUS: Draft
TYPE: Functional
COMPONENT: Tracing
TITLE: Tracing Object Identification
STATEMENT: >>>
Zephyr shall provide an interface to identify the objects being traced.
<<<
USER_STORY: >>>
As a Zephyr OS user, I want to be able to give each object which I create a name / label in order to be able to identify them in a trace log.
<<<
RELATIONS:
- TYPE: Parent
  VALUE: ZEP-SYRS-19

[REQUIREMENT]
UID: ZEP-SRS-10-6
STATUS: Draft
TYPE: Functional
COMPONENT: Tracing
TITLE: Tracing Non-Interference
STATEMENT: >>>
Zephyr shall prevent the tracing functionality from interfering with normal operations.
<<<
USER_STORY: >>>
As a Zephyr OS user, I want that the trace functionality do not interfere or slow down the operation system functionality.
<<<
RELATIONS:
- TYPE: Parent
  VALUE: ZEP-SYRS-19

[REQUIREMENT]
UID: ZEP-SRS-10-7
STATUS: Draft
TYPE: Functional
COMPONENT: Tracing
TITLE: Tracing kernel events
STATEMENT: >>>
The Zephyr RTOS shall support tracing of kernel events in each of the following
categories: thread lifecycle and scheduling including context switches, interrupt
entry and exit, system call entry and exit, operations on kernel synchronization and
data passing objects, work queue operations, memory allocator operations, timers,
and polling.
<<<
RELATIONS:
- TYPE: Parent
  VALUE: ZEP-SYRS-19

[REQUIREMENT]
UID: ZEP-SRS-10-8
STATUS: Draft
TYPE: Functional
COMPONENT: Tracing
TITLE: Configurable tracing
STATEMENT: >>>
The Zephyr RTOS shall allow tracing to be enabled or disabled through configuration,
at build time.
<<<
RELATIONS:
- TYPE: Parent
  VALUE: ZEP-SYRS-19

[REQUIREMENT]
UID: ZEP-SRS-10-9
STATUS: Draft
TYPE: Functional
COMPONENT: Tracing
TITLE: Tracing backends
STATEMENT: >>>
The Zephyr RTOS shall emit trace data through a tracing backend selected at build
time from the available backends.
<<<
RELATIONS:
- TYPE: Parent
  VALUE: ZEP-SYRS-19

[REQUIREMENT]
UID: ZEP-SRS-10-10
STATUS: Draft
TYPE: Functional
COMPONENT: Tracing
TITLE: Trace data emission modes
STATEMENT: >>>
The Zephyr RTOS shall support emitting trace data synchronously and through a buffered mode.
<<<
RELATIONS:
- TYPE: Parent
  VALUE: ZEP-SYRS-19

[REQUIREMENT]
UID: ZEP-SRS-10-11
STATUS: Draft
TYPE: Functional
COMPONENT: Tracing
TITLE: Per-category trace configuration
STATEMENT: >>>
The Zephyr RTOS shall allow tracing to be enabled or disabled for each kernel event
category individually through configuration, at build time.
<<<
RELATIONS:
- TYPE: Parent
  VALUE: ZEP-SYRS-19
