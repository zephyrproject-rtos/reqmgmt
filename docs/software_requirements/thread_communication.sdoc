[DOCUMENT]
TITLE: Thread Communication
REQ_PREFIX: ZEP-SRS-3-

[GRAMMAR]
IMPORT_FROM_FILE: software_requirements.sgra

[TEXT]
STATEMENT: >>>
SPDX-License-Identifier: Apache-2.0
<<<

[TEXT]
STATEMENT: >>>
Thread communication comprises the kernel objects and mechanisms that allow
threads, and threads and interrupt service routines, to exchange data and to
coordinate their execution.

The Zephyr RTOS provides the following thread communication mechanisms, each
specified in its own requirements document:

- Message Queues
- Pipes
- Mailboxes
- Polling
<<<
