[DOCUMENT]
TITLE: Queues
REQ_PREFIX: ZEP-SRS-20-

[GRAMMAR]
IMPORT_FROM_FILE: software_requirements.sgra

[REQUIREMENT]
UID: ZEP-SRS-20-1
STATUS: Draft
TYPE: Functional
COMPONENT: Queues
TITLE: Queue definition at compile time
STATEMENT: >>>
The Zephyr RTOS shall provide a mechanism to define and initialize a queue at compile time.
<<<
RELATIONS:
- TYPE: Parent
  VALUE: ZEP-SYRS-22

[REQUIREMENT]
UID: ZEP-SRS-20-2
STATUS: Draft
TYPE: Functional
COMPONENT: Queues
TITLE: Queue definition at run time.
STATEMENT: >>>
The Zephyr RTOS shall provide a mechanism to define and initialize a queue at run time.
<<<
RELATIONS:
- TYPE: Parent
  VALUE: ZEP-SYRS-22

[REQUIREMENT]
UID: ZEP-SRS-20-3
STATUS: Draft
TYPE: Functional
COMPONENT: Queues
TITLE: Queue enqueue item to the back
STATEMENT: >>>
The Zephyr RTOS shall provide a mechanism to enqueue a data item to the back of a queue (i.e. append).
<<<
RELATIONS:
- TYPE: Parent
  VALUE: ZEP-SYRS-22

[REQUIREMENT]
UID: ZEP-SRS-20-4
STATUS: Draft
TYPE: Functional
COMPONENT: Queues
TITLE: Queue enqueue item to the front
STATEMENT: >>>
The Zephyr RTOS shall provide a mechanism to enqueue a data item to the front of a queue (i.e. prepend).
<<<
RELATIONS:
- TYPE: Parent
  VALUE: ZEP-SYRS-22

[REQUIREMENT]
UID: ZEP-SRS-20-5
STATUS: Draft
TYPE: Functional
COMPONENT: Queues
TITLE: Queue remove item
STATEMENT: >>>
The Zephyr RTOS shall provide a mechanism to remove a specific data item from a queue.
<<<
RELATIONS:
- TYPE: Parent
  VALUE: ZEP-SYRS-22

[REQUIREMENT]
UID: ZEP-SRS-20-6
STATUS: Draft
TYPE: Functional
COMPONENT: Queues
TITLE: Queue get and dequeue item from front
STATEMENT: >>>
The Zephyr RTOS shall provide a mechanism to get and dequeue a data item from the front of a queue, within a timeout.
<<<
RELATIONS:
- TYPE: Parent
  VALUE: ZEP-SYRS-22

[REQUIREMENT]
UID: ZEP-SRS-20-7
STATUS: Draft
TYPE: Functional
COMPONENT: Queues
TITLE: Queue empty check
STATEMENT: >>>
The Zephyr RTOS shall provide a mechanism to check if a queue is empty.
<<<
RELATIONS:
- TYPE: Parent
  VALUE: ZEP-SYRS-22

[REQUIREMENT]
UID: ZEP-SRS-20-8
STATUS: Draft
TYPE: Functional
COMPONENT: Queues
TITLE: Queue peek item at back
STATEMENT: >>>
The Zephyr RTOS shall provide a mechanism to peek at the data item at the back of a queue.
<<<
RELATIONS:
- TYPE: Parent
  VALUE: ZEP-SYRS-22

[REQUIREMENT]
UID: ZEP-SRS-20-9
STATUS: Draft
TYPE: Functional
COMPONENT: Queues
TITLE: Queue peek item at front
STATEMENT: >>>
The Zephyr RTOS shall provide a mechanism to peek at the data item at the front of a queue.
<<<
RELATIONS:
- TYPE: Parent
  VALUE: ZEP-SYRS-22

[REQUIREMENT]
UID: ZEP-SRS-20-10
STATUS: Draft
TYPE: Functional
COMPONENT: Queues
TITLE: Queue insert
STATEMENT: >>>
The Zephyr RTOS shall provide a mechanism to insert a data item behind another specific data item in a queue.
<<<
RELATIONS:
- TYPE: Parent
  VALUE: ZEP-SYRS-22

[REQUIREMENT]
UID: ZEP-SRS-20-11
STATUS: Draft
TYPE: Functional
COMPONENT: Queues
TITLE: Queue append item list to the back
STATEMENT: >>>
The Zephyr RTOS shall provide a mechanism to append a list of data items to the back of a queue.
<<<
RELATIONS:
- TYPE: Parent
  VALUE: ZEP-SYRS-22

[REQUIREMENT]
UID: ZEP-SRS-20-12
STATUS: Draft
TYPE: Functional
COMPONENT: Queues
TITLE: Queue append and empty item list to the back
STATEMENT: >>>
The Zephyr RTOS shall provide a mechanism to append a list of data items to the back of a queue and then empty the list.
<<<
RELATIONS:
- TYPE: Parent
  VALUE: ZEP-SYRS-22

[REQUIREMENT]
UID: ZEP-SRS-20-13
STATUS: Draft
TYPE: Functional
COMPONENT: Queues
TITLE: Queue append unique data item
STATEMENT: >>>
The Zephyr RTOS shall provide a mechanism to append a data item uniquely to the queue.
<<<
RELATIONS:
- TYPE: Parent
  VALUE: ZEP-SYRS-22

[REQUIREMENT]
UID: ZEP-SRS-20-14
STATUS: Draft
TYPE: Functional
COMPONENT: Queues
TITLE: Queue implicit memory allocation
STATEMENT: >>>
The Zephyr RTOS shall provide a dedicated mechanism to implicite allocate memory from a thread when appending
data items to a queue.
<<<
RELATIONS:
- TYPE: Parent
  VALUE: ZEP-SYRS-22

[REQUIREMENT]
UID: ZEP-SRS-20-15
STATUS: Draft
TYPE: Functional
COMPONENT: Queues
TITLE: Queue cancel waiting thread
STATEMENT: >>>
The Zephyr RTOS shall provide a mechanism to cause the highest-priority, longest-waiting
thread waiting to get an item from a queue to return as if its timeout had expired.
<<<
RELATIONS:
- TYPE: Parent
  VALUE: ZEP-SYRS-22

[REQUIREMENT]
UID: ZEP-SRS-20-16
STATUS: Draft
TYPE: Functional
COMPONENT: Queues
TITLE: Queue data item handover order
STATEMENT: >>>
When a data item becomes available in a queue on which one or more threads are waiting to
get and dequeue a data item, the Zephyr RTOS shall hand the data item to the
highest-priority, longest-waiting thread.
<<<
RELATIONS:
- TYPE: Parent
  VALUE: ZEP-SYRS-22

[REQUIREMENT]
UID: ZEP-SRS-20-17
STATUS: Draft
TYPE: Functional
COMPONENT: Queues
TITLE: Blocking get from an empty queue
STATEMENT: >>>
When a thread attempts to get and dequeue a data item from an empty queue with a timeout
other than K_NO_WAIT, the Zephyr RTOS shall block the thread until a data item becomes
available or the timeout expires, whichever occurs first.
<<<
RELATIONS:
- TYPE: Parent
  VALUE: ZEP-SYRS-22

[REQUIREMENT]
UID: ZEP-SRS-20-18
STATUS: Draft
TYPE: Functional
COMPONENT: Queues
TITLE: Get from an empty queue when the timeout expires
STATEMENT: >>>
When the timeout of a thread blocked while getting and dequeuing a data item from an empty
queue expires before a data item becomes available, the Zephyr RTOS shall return to the
thread without a data item and indicate that no data item was obtained.
<<<
RELATIONS:
- TYPE: Parent
  VALUE: ZEP-SYRS-22

[REQUIREMENT]
UID: ZEP-SRS-20-19
STATUS: Draft
TYPE: Functional
COMPONENT: Queues
TITLE: Get from an empty queue with K_NO_WAIT
STATEMENT: >>>
When a thread attempts to get and dequeue a data item from an empty queue with a timeout
of K_NO_WAIT, the Zephyr RTOS shall return to the thread immediately without a data item
and indicate that no data item was obtained.
<<<
RELATIONS:
- TYPE: Parent
  VALUE: ZEP-SYRS-22
