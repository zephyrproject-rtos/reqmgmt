[DOCUMENT]
TITLE: Device Driver API
REQ_PREFIX: ZEP-SRS-14-

[GRAMMAR]
IMPORT_FROM_FILE: software_requirements.sgra

[TEXT]
STATEMENT: >>>
SPDX-License-Identifier: Apache-2.0
<<<

[REQUIREMENT]
UID: ZEP-SRS-14-1
STATUS: Draft
TYPE: Functional
COMPONENT: Device Driver API
TITLE: Device Driver Abstraction
STATEMENT: >>>
The Zephyr RTOS shall provide an interface between applications and individual device drivers that abstracts common device driver functionality.
<<<
RELATIONS:
- TYPE: Parent
  VALUE: ZEP-SYRS-4

[REQUIREMENT]
UID: ZEP-SRS-14-2
STATUS: Draft
TYPE: Functional
COMPONENT: Device Driver API
TITLE: Expose kernel to hardware interrupts
STATEMENT: >>>
The Zephyr RTOS shall provide an interface for managing a defined set of hardware exceptions (including interrupts) across all systems.
<<<
USER_STORY: >>>
As a Zephyr RTOS user I want hardware exceptions (hardware failures, programming mistakes) to be handled gracefully (no program crashes as far as possible).
<<<
RELATIONS:
- TYPE: Parent
  VALUE: ZEP-SYRS-4

[REQUIREMENT]
UID: ZEP-SRS-14-3
STATUS: Draft
TYPE: Functional
COMPONENT: Device Driver API
TITLE: Defining a device
STATEMENT: >>>
The Zephyr RTOS shall provide a mechanism to define a device at build time.
<<<
RELATIONS:
- TYPE: Parent
  VALUE: ZEP-SYRS-4

[REQUIREMENT]
UID: ZEP-SRS-14-21
STATUS: Draft
TYPE: Functional
COMPONENT: Device Driver API
TITLE: Device initialization function
STATEMENT: >>>
Where a device defines an initialization function, the Zephyr RTOS shall initialize
the device by invoking that function.
<<<
RELATIONS:
- TYPE: Parent
  VALUE: ZEP-SYRS-4

[REQUIREMENT]
UID: ZEP-SRS-14-4
STATUS: Draft
TYPE: Functional
COMPONENT: Device Driver API
TITLE: Obtaining a device by name
STATEMENT: >>>
The Zephyr RTOS shall provide a mechanism to obtain, at run time, a reference to a
device by its name, the string assigned to the device when it is defined.
<<<
RELATIONS:
- TYPE: Parent
  VALUE: ZEP-SYRS-4

[REQUIREMENT]
UID: ZEP-SRS-14-22
STATUS: Draft
TYPE: Functional
COMPONENT: Device Driver API
TITLE: Device lookup by name yields no reference for unavailable devices
STATEMENT: >>>
When a device reference is requested by name and no device matches the requested
name, or the matching device is not ready, the Zephyr RTOS shall return no device
reference.
<<<
RELATIONS:
- TYPE: Parent
  VALUE: ZEP-SYRS-4

[REQUIREMENT]
UID: ZEP-SRS-14-13
STATUS: Draft
TYPE: Functional
COMPONENT: Device Driver API
TITLE: Obtaining a device by definition name
STATEMENT: >>>
The Zephyr RTOS shall provide a mechanism to obtain, at build time, a reference to a
device by the identifier assigned to the device at its definition.
<<<
RELATIONS:
- TYPE: Parent
  VALUE: ZEP-SYRS-4

[REQUIREMENT]
UID: ZEP-SRS-14-5
STATUS: Draft
TYPE: Functional
COMPONENT: Device Driver API
TITLE: Obtaining a device from a devicetree node
STATEMENT: >>>
The Zephyr RTOS shall provide a mechanism to obtain, at build time, a reference to a
device from its devicetree node.
<<<
RELATIONS:
- TYPE: Parent
  VALUE: ZEP-SYRS-4

[REQUIREMENT]
UID: ZEP-SRS-14-14
STATUS: Draft
TYPE: Functional
COMPONENT: Device Driver API
TITLE: Obtaining a device by devicetree compatible
STATEMENT: >>>
The Zephyr RTOS shall provide a mechanism to obtain, at build time, a reference to an
enabled device matching a devicetree compatible.
<<<
RELATIONS:
- TYPE: Parent
  VALUE: ZEP-SYRS-4

[REQUIREMENT]
UID: ZEP-SRS-14-31
STATUS: Draft
TYPE: Functional
COMPONENT: Device Driver API
TITLE: Multiple devices matching a compatible
STATEMENT: >>>
When more than one enabled device matches a devicetree compatible requested through
a build-time reference by compatible, the Zephyr RTOS shall return a reference to
one of the matching devices.
<<<
RELATIONS:
- TYPE: Parent
  VALUE: ZEP-SYRS-4

[REQUIREMENT]
UID: ZEP-SRS-14-29
STATUS: Draft
TYPE: Functional
COMPONENT: Device Driver API
TITLE: No device matching a compatible
STATEMENT: >>>
If no enabled device matches the devicetree compatible requested through the
arbitrary-device reference mechanism, then the Zephyr RTOS shall return no device
reference.
<<<
RELATIONS:
- TYPE: Parent
  VALUE: ZEP-SYRS-4

[REQUIREMENT]
UID: ZEP-SRS-14-23
STATUS: Draft
TYPE: Functional
COMPONENT: Device Driver API
TITLE: Required device reference by devicetree compatible
STATEMENT: >>>
The Zephyr RTOS shall provide a build-time mechanism that returns a reference to a
device matching a devicetree compatible and that fails the build when no enabled
device of that compatible exists.
<<<
RELATIONS:
- TYPE: Parent
  VALUE: ZEP-SYRS-4

[REQUIREMENT]
UID: ZEP-SRS-14-15
STATUS: Draft
TYPE: Functional
COMPONENT: Device Driver API
TITLE: Obtaining a device by instance index
STATEMENT: >>>
The Zephyr RTOS shall provide a mechanism for a driver to obtain, at build time, a
reference to a device by the instance number of the devicetree nodes matching
the driver's compatible.
<<<
RELATIONS:
- TYPE: Parent
  VALUE: ZEP-SYRS-4

[REQUIREMENT]
UID: ZEP-SRS-14-6
STATUS: Draft
TYPE: Functional
COMPONENT: Device Driver API
TITLE: Checking device readiness
STATEMENT: >>>
The Zephyr RTOS shall provide a mechanism to determine whether a device is ready to be used.
<<<
RELATIONS:
- TYPE: Parent
  VALUE: ZEP-SYRS-4

[REQUIREMENT]
UID: ZEP-SRS-14-24
STATUS: Draft
TYPE: Functional
COMPONENT: Device Driver API
TITLE: Readiness of an invalid device reference
STATEMENT: >>>
If an invalid device reference is passed to the readiness check, then the Zephyr RTOS
shall report it as not ready.
<<<
RELATIONS:
- TYPE: Parent
  VALUE: ZEP-SYRS-4

[REQUIREMENT]
UID: ZEP-SRS-14-25
STATUS: Draft
TYPE: Functional
COMPONENT: Device Driver API
TITLE: Device readiness condition
STATEMENT: >>>
The Zephyr RTOS shall report a device as ready only when its initialization
has completed successfully.
<<<
RELATIONS:
- TYPE: Parent
  VALUE: ZEP-SYRS-4

[REQUIREMENT]
UID: ZEP-SRS-14-7
STATUS: Draft
TYPE: Functional
COMPONENT: Device Driver API
TITLE: Deferred device initialization
STATEMENT: >>>
The Zephyr RTOS shall provide a mechanism to mark, at build time, a device
for deferred initialization.
<<<
RELATIONS:
- TYPE: Parent
  VALUE: ZEP-SYRS-4

[REQUIREMENT]
UID: ZEP-SRS-14-26
STATUS: Draft
TYPE: Functional
COMPONENT: Device Driver API
TITLE: Skipping deferred devices at startup
STATEMENT: >>>
When system initialization occurs, the Zephyr RTOS shall not initialize devices
marked for deferred initialization.
<<<
RELATIONS:
- TYPE: Parent
  VALUE: ZEP-SYRS-4

[REQUIREMENT]
UID: ZEP-SRS-14-27
STATUS: Draft
TYPE: Functional
COMPONENT: Device Driver API
TITLE: Run-time device initialization
STATEMENT: >>>
The Zephyr RTOS shall provide a mechanism to initialize a device at run
time.
<<<
RELATIONS:
- TYPE: Parent
  VALUE: ZEP-SYRS-4

[REQUIREMENT]
UID: ZEP-SRS-14-8
STATUS: Draft
TYPE: Functional
COMPONENT: Device Driver API
TITLE: Reporting deferred initialization failure
STATEMENT: >>>
If a deferred device initialization fails, then the Zephyr RTOS shall return an
error and leave the device in a not-ready state.
<<<
RELATIONS:
- TYPE: Parent
  VALUE: ZEP-SYRS-4

[REQUIREMENT]
UID: ZEP-SRS-14-16
STATUS: Draft
TYPE: Functional
COMPONENT: Device Driver API
TITLE: Initializing an already initialized device
STATEMENT: >>>
If initialization is requested for a device that has already been initialized, then
the Zephyr RTOS shall return an error indicating the device is already initialized.
<<<
RELATIONS:
- TYPE: Parent
  VALUE: ZEP-SYRS-4

[REQUIREMENT]
UID: ZEP-SRS-14-9
STATUS: Draft
TYPE: Functional
COMPONENT: Device Driver API
TITLE: De-initializing a device
STATEMENT: >>>
The Zephyr RTOS shall provide a mechanism to de-initialize a device at run time.
<<<
RELATIONS:
- TYPE: Parent
  VALUE: ZEP-SYRS-4

[REQUIREMENT]
UID: ZEP-SRS-14-30
STATUS: Draft
TYPE: Functional
COMPONENT: Device Driver API
TITLE: De-initialization not enabled
STATEMENT: >>>
Where device de-initialization is not enabled, if de-initialization of a device is
requested, then the Zephyr RTOS shall return an error indicating the operation is
not supported.
<<<
RELATIONS:
- TYPE: Parent
  VALUE: ZEP-SYRS-4

[REQUIREMENT]
UID: ZEP-SRS-14-10
STATUS: Draft
TYPE: Functional
COMPONENT: Device Driver API
TITLE: Rejecting de-initialization of an unsupported device
STATEMENT: >>>
Where device de-initialization is enabled, if de-initialization is requested for a
device that does not provide a de-initialization function, then the Zephyr RTOS shall
report that the operation is not supported.
<<<
RELATIONS:
- TYPE: Parent
  VALUE: ZEP-SYRS-4

[REQUIREMENT]
UID: ZEP-SRS-14-28
STATUS: Draft
TYPE: Functional
COMPONENT: Device Driver API
TITLE: Failed device de-initialization
STATEMENT: >>>
Where device de-initialization is enabled, if the de-initialization of a device
fails, then the Zephyr RTOS shall return an error and leave the device in the ready
state.
<<<
RELATIONS:
- TYPE: Parent
  VALUE: ZEP-SYRS-4

[REQUIREMENT]
UID: ZEP-SRS-14-17
STATUS: Draft
TYPE: Functional
COMPONENT: Device Driver API
TITLE: Device readiness after de-initialization
STATEMENT: >>>
Where device de-initialization is enabled, when a device is de-initialized, the
Zephyr RTOS shall report the device as not ready.
<<<
RELATIONS:
- TYPE: Parent
  VALUE: ZEP-SYRS-4

[REQUIREMENT]
UID: ZEP-SRS-14-18
STATUS: Draft
TYPE: Functional
COMPONENT: Device Driver API
TITLE: Re-initializing a de-initialized device
STATEMENT: >>>
Where device de-initialization is enabled, the Zephyr RTOS shall allow a
de-initialized device to be initialized again at run time.
<<<
RELATIONS:
- TYPE: Parent
  VALUE: ZEP-SYRS-4

[REQUIREMENT]
UID: ZEP-SRS-14-19
STATUS: Draft
TYPE: Functional
COMPONENT: Device Driver API
TITLE: De-initializing an uninitialized device
STATEMENT: >>>
Where device de-initialization is enabled, if de-initialization is requested for a
device that is not ready, then the Zephyr RTOS shall return an error indicating the
operation is not permitted.
<<<
RELATIONS:
- TYPE: Parent
  VALUE: ZEP-SYRS-4

[REQUIREMENT]
UID: ZEP-SRS-14-11
STATUS: Draft
TYPE: Functional
COMPONENT: Device Driver API
TITLE: Querying the devices a device depends on
STATEMENT: >>>
Where device dependencies are stored, the Zephyr RTOS shall provide a mechanism to
query the set of devices that a device depends on.
<<<
RELATIONS:
- TYPE: Parent
  VALUE: ZEP-SYRS-4

[REQUIREMENT]
UID: ZEP-SRS-14-20
STATUS: Draft
TYPE: Functional
COMPONENT: Device Driver API
TITLE: Querying the devices that depend on a device
STATEMENT: >>>
Where device dependencies are stored, the Zephyr RTOS shall provide a mechanism to
query the set of devices that depend on a device.
<<<
RELATIONS:
- TYPE: Parent
  VALUE: ZEP-SYRS-4

[REQUIREMENT]
UID: ZEP-SRS-14-12
STATUS: Draft
TYPE: Functional
COMPONENT: Device Driver API
TITLE: Obtaining a device by devicetree node label
STATEMENT: >>>
Where devicetree device metadata is stored, the Zephyr RTOS shall provide a mechanism to obtain a reference to a device by its devicetree node label.
<<<
RELATIONS:
- TYPE: Parent
  VALUE: ZEP-SYRS-4
