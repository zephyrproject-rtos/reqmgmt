[DOCUMENT]
TITLE: Scheduling
REQ_PREFIX: ZEP-SRS-23-

[GRAMMAR]
IMPORT_FROM_FILE: software_requirements.sgra

[TEXT]
STATEMENT: >>>
SPDX-License-Identifier: Apache-2.0
<<<

[SECTION]
TITLE: Thread Scheduling Algorithm

[REQUIREMENT]
UID: ZEP-SRS-23-001
STATUS: Active
TYPE: Functional
COMPONENT: Thread Scheduling
TITLE: Priority-Based Selection
STATEMENT: >>>
The Zephyr RTOS shall select the highest-priority ready thread permitted to execute on the current CPU as the current thread.
<<<

[REQUIREMENT]
UID: ZEP-SRS-23-002
STATUS: Active
TYPE: Functional
COMPONENT: Scheduling
TITLE: Earliest Deadline First Scheduling
STATEMENT: >>>
When earliest-deadline-first (EDF) scheduling is enabled, the scheduler shall only consider the deadline when prioritizing between threads of equal static priority. The thread with the earliest deadline shall be considered to have the higher priority.
<<<
USER_STORY: >>>
As a Zephyr RTOS user, I want to be able to schedule threads by earliest deadline first.
<<<

[REQUIREMENT]
UID: ZEP-SRS-23-003
STATUS: Active
TYPE: Non-Functional
COMPONENT: Scheduling
TITLE: Ready Queue Scalability
STATEMENT: >>>
The Zephyr RTOS shall support ready queue implementations that are configurable at build time.
<<<

[/SECTION]

[SECTION]
TITLE: Reschedule Points

[REQUIREMENT]
UID: ZEP-SRS-23-004
STATUS: Active
TYPE: Functional
COMPONENT: Scheduling
TITLE: Mandatory Context Switch Triggers
STATEMENT: >>>
The Zephyr RTOS shall trigger rescheduling when: a thread becomes blocked or ready, a thread's static priority is modified, an ISR returns to thread context, a thread voluntarily yields, a time slice expires, or the scheduler is unlocked.
<<<

[REQUIREMENT]
UID: ZEP-SRS-23-005
STATUS: Active
TYPE: Functional
COMPONENT: Scheduling
TITLE: Atomic Rescheduling
STATEMENT: >>>
Rescheduling shall both occur at designated points and be atomic to prevent partial state corruption during thread swaps.
<<<

[/SECTION]

[SECTION]
TITLE: Thread States and Priorities

[REQUIREMENT]
UID: ZEP-SRS-23-006
STATUS: Active
TYPE: Functional
COMPONENT: Scheduling
TITLE: Cooperative Thread Non-Preemption
STATEMENT: >>>
The Zephyr RTOS shall ensure cooperative threads (negative static priority) retain execution until explicitly yielding or entering an unready state, except when preempted by Meta-IRQ threads.
<<<
USER_STORY: >>>
As a Zephyr RTOS user, I want to be able to configure thread prioritizes which cannot be preempted by other user threads.
<<<

[REQUIREMENT]
UID: ZEP-SRS-23-007
STATUS: Active
TYPE: Functional
COMPONENT: Scheduling
TITLE: Preemptive Thread Preemption
STATEMENT: >>>
The Zephyr RTOS shall preempt preemptive threads (non-negative static priority) when a higher-priority ready thread becomes available at a reschedule point.
<<<
USER_STORY: >>>
As a Zephyr RTOS user, I want that the OS preempt running threads by a thread with higher priority.
<<<

[/SECTION]

[SECTION]
TITLE: Time Slicing

[REQUIREMENT]
UID: ZEP-SRS-23-008
STATUS: Active
TYPE: Functional
COMPONENT: Scheduling
TITLE: Voluntary Yielding
STATEMENT: >>>
The Zephyr RTOS shall provide a mechanism for a thread to voluntarily cede control of the CPU to a thread of equal or higher priority if any exist.
<<<

[REQUIREMENT]
UID: ZEP-SRS-23-009
STATUS: Active
TYPE: Functional
COMPONENT: Scheduling
TITLE: Preemptive Time Quantum
STATEMENT: >>>
Where time slicing is enabled, preemptive threads shall relinquish the CPU after not more than a configurable number of system ticks if there is another ready thread of equal priority.
<<<

[REQUIREMENT]
UID: ZEP-SRS-23-017
STATUS: Active
TYPE: Functional
COMPONENT: Scheduling
TITLE: Time Slice Priority Exemption
STATEMENT: >>>
Where time slicing is enabled, threads with priority higher than a configurable threshold shall be exempt from preemptive time slicing.
<<<

[/SECTION]

[SECTION]
TITLE: Thread Management

[REQUIREMENT]
UID: ZEP-SRS-23-
STATUS: Draft
TYPE: Functional
COMPONENT: Scheduling
TITLE: Scheduling multiple threads
STATEMENT: >>>
The Zephyr RTOS shall provide an interface to schedule multiple threads.
<<<
RELATIONS:
- TYPE: Parent
  VALUE: ZEP-SYRS-16

[REQUIREMENT]
UID: ZEP-SRS-23-010
STATUS: Active
TYPE: Functional
COMPONENT: Scheduling
TITLE: Non-Preemptible Critical Sections
STATEMENT: >>>
The Zephyr RTOS shall provide a mechanism to temporarily prevent preemption of a preemptive thread until the mechanism is explicitly released. If the thread becomes unready while preemption is prevented, the non-preemptible status shall be maintained when the thread resumes.
<<<

[REQUIREMENT]
UID: ZEP-SRS-23-011
STATUS: Active
TYPE: Functional
COMPONENT: Scheduling
TITLE: Thread Sleeping
STATEMENT: >>>
The Zephyr RTOS shall provide a mechanism to delay thread execution for a specified time period, relinquishing the CPU to other ready threads. A sleeping thread may be awakened prematurely by another thread.
<<<

[REQUIREMENT]
UID: ZEP-SRS-23-013
STATUS: Active
TYPE: Functional
COMPONENT: Scheduling
TITLE: Thread Waking
STATEMENT: >>>
The Zephyr RTOS shall provide a mechanism to for a thread to wake another thread. Note: A wakeup can be attempted on a thread that is already awake - this has no effect.
<<<

[REQUIREMENT]
UID: ZEP-SRS-23-012
STATUS: Active
TYPE: Functional
COMPONENT: Scheduling
TITLE: Busy Wait Non-Relinquishing
STATEMENT: >>>
The Zephyr RTOS shall provide a mechanism to delay thread execution for a specified duration without relinquishing the CPU or triggering rescheduling.
<<<

[/SECTION]

[SECTION]
TITLE: SMP Considerations

[REQUIREMENT]
UID: ZEP-SRS-23-015
STATUS: Active
TYPE: Functional
COMPONENT: Scheduling
TITLE: Deterministic Latency
STATEMENT: >>>
Worst-case context switch latency shall be ≤X μs (platform-specific).
<<<

[REQUIREMENT]
UID: ZEP-SRS-23-016
STATUS: Active
TYPE: Functional
COMPONENT: Scheduling
TITLE: Scheduler Data Structure Mutual Exclusion
STATEMENT: >>>
Scheduler data structures that require cross-CPU mutual exclusion shall be guarded by spinlocks.
<<<

[/SECTION]
