[DOCUMENT]
TITLE: Multicore and SMP
REQ_PREFIX: ZEP-SRS-34-

[GRAMMAR]
IMPORT_FROM_FILE: software_requirements.sgra

[TEXT]
STATEMENT: >>>
SPDX-License-Identifier: Apache-2.0
<<<

[REQUIREMENT]
UID: ZEP-SRS-34-1
STATUS: Draft
TYPE: Functional
COMPONENT: Multi Core
TITLE: Support operation on more than one CPU
STATEMENT: >>>
The Zephyr RTOS shall support operation on more than one physical CPU sharing the same kernel state.
<<<
RELATIONS:
- TYPE: Parent
  VALUE: ZEP-SYRS-11

[REQUIREMENT]
UID: ZEP-SRS-34-2
STATUS: Draft
TYPE: Functional
COMPONENT: Multi Core
TITLE: Running threads on specific CPUs
STATEMENT: >>>
The Zephyr RTOS shall provide an interface to specify the set of CPUs on which a thread is eligible to execute.
<<<
USER_STORY: >>>
As a Zephyr RTOS user I want Zephyr OS to be able to specify the CPU core or the set of CPU cores on which a thread shall be executed.
<<<
RELATIONS:
- TYPE: Parent
  VALUE: ZEP-SYRS-12

[REQUIREMENT]
UID: ZEP-SRS-34-21
STATUS: Draft
TYPE: Functional
COMPONENT: Multi Core
TITLE: Default CPU eligibility
STATEMENT: >>>
When no CPU set has been specified for a thread, the Zephyr RTOS shall consider the thread eligible to execute on any CPU.
<<<
RELATIONS:
- TYPE: Parent
  VALUE: ZEP-SYRS-12

[REQUIREMENT]
UID: ZEP-SRS-34-3
STATUS: Draft
TYPE: Functional
COMPONENT: Multi Core
TITLE: Exclusion between physical CPUs
STATEMENT: >>>
The Zephyr RTOS shall provide an interface for mutual exclusion between multiple physical CPUs.
<<<
USER_STORY: >>>
As a Zephyr RTOS user I want Zephyr OS to provide synchronization mechanisms between the CPU cores and the access to common resources.
<<<
RELATIONS:
- TYPE: Parent
  VALUE: ZEP-SYRS-11

[REQUIREMENT]
UID: ZEP-SRS-34-4
STATUS: Draft
TYPE: Functional
COMPONENT: Multi Core
TITLE: Configurable maximum number of CPUs
STATEMENT: >>>
The Zephyr RTOS shall support a configurable maximum number of CPUs.
<<<
RELATIONS:
- TYPE: Parent
  VALUE: ZEP-SYRS-2

[REQUIREMENT]
UID: ZEP-SRS-34-5
STATUS: Draft
TYPE: Functional
COMPONENT: Multi Core
TITLE: Secondary CPU bring-up during initialization
STATEMENT: >>>
During kernel initialization, the Zephyr RTOS shall bring up the secondary CPUs and make them available for thread scheduling.
<<<
RELATIONS:
- TYPE: Parent
  VALUE: ZEP-SYRS-11

[REQUIREMENT]
UID: ZEP-SRS-34-6
STATUS: Draft
TYPE: Functional
COMPONENT: Multi Core
TITLE: Per-CPU initialization
STATEMENT: >>>
Before a CPU begins to participate in thread scheduling, the Zephyr RTOS shall initialize that CPU's per-CPU kernel data.
<<<
RELATIONS:
- TYPE: Parent
  VALUE: ZEP-SYRS-11

[REQUIREMENT]
UID: ZEP-SRS-34-7
STATUS: Draft
TYPE: Functional
COMPONENT: Multi Core
TITLE: Starting a CPU at run time
STATEMENT: >>>
The Zephyr RTOS shall provide a mechanism to start, at run time, a CPU that is in an off state, after which the CPU participates in thread scheduling and execution.
<<<
RELATIONS:
- TYPE: Parent
  VALUE: ZEP-SYRS-11

[REQUIREMENT]
UID: ZEP-SRS-34-8
STATUS: Draft
TYPE: Functional
COMPONENT: Multi Core
TITLE: Invoking a function on a started CPU
STATEMENT: >>>
When starting a CPU at run time, the Zephyr RTOS shall invoke a caller-supplied function on that CPU before the CPU enters the scheduler.
<<<
RELATIONS:
- TYPE: Parent
  VALUE: ZEP-SYRS-11

[REQUIREMENT]
UID: ZEP-SRS-34-9
STATUS: Draft
TYPE: Functional
COMPONENT: Multi Core
TITLE: Resuming a suspended CPU
STATEMENT: >>>
The Zephyr RTOS shall provide a mechanism to resume a previously started CPU that has reached an idle or off state, without re-initializing the kernel's per-CPU data for that CPU.
<<<
RELATIONS:
- TYPE: Parent
  VALUE: ZEP-SYRS-11

[REQUIREMENT]
UID: ZEP-SRS-34-10
STATUS: Draft
TYPE: Functional
COMPONENT: Multi Core
TITLE: Concurrent scheduling across CPUs
STATEMENT: >>>
Where symmetric multiprocessing is enabled, the Zephyr RTOS shall schedule the highest-priority ready threads to run concurrently across the available CPUs.
<<<
RELATIONS:
- TYPE: Parent
  VALUE: ZEP-SYRS-11

[REQUIREMENT]
UID: ZEP-SRS-34-11
STATUS: Draft
TYPE: Functional
COMPONENT: Multi Core
TITLE: Inter-processor reschedule signaling
STATEMENT: >>>
When a scheduling change makes a thread eligible to run on a different CPU, the Zephyr RTOS shall signal that CPU to perform a reschedule, by an inter-processor interrupt where the hardware supports it.
<<<
RELATIONS:
- TYPE: Parent
  VALUE: ZEP-SYRS-11

[REQUIREMENT]
UID: ZEP-SRS-34-12
STATUS: Draft
TYPE: Functional
COMPONENT: Multi Core
TITLE: Pinning a thread to a CPU
STATEMENT: >>>
Where CPU affinity is enabled, the Zephyr RTOS shall provide a mechanism to pin a thread so that it runs on a single specified CPU.
<<<
RELATIONS:
- TYPE: Parent
  VALUE: ZEP-SYRS-12

[REQUIREMENT]
UID: ZEP-SRS-34-13
STATUS: Draft
TYPE: Functional
COMPONENT: Multi Core
TITLE: Restriction on changing CPU affinity
STATEMENT: >>>
The Zephyr RTOS shall allow a thread's CPU affinity to be modified only while the thread is not runnable.
<<<
RELATIONS:
- TYPE: Parent
  VALUE: ZEP-SYRS-12

[REQUIREMENT]
UID: ZEP-SRS-34-14
STATUS: Draft
TYPE: Functional
COMPONENT: Multi Core
TITLE: Deferred secondary CPU boot
STATEMENT: >>>
Where deferred secondary CPU boot is enabled, the Zephyr RTOS shall not bring up the secondary CPUs during kernel initialization, leaving them to be started later at run time.
<<<
RELATIONS:
- TYPE: Parent
  VALUE: ZEP-SYRS-11

[REQUIREMENT]
UID: ZEP-SRS-34-15
STATUS: Draft
TYPE: Functional
COMPONENT: Multi Core
TITLE: Single-CPU pin-only affinity
STATEMENT: >>>
Where single-CPU pin-only affinity is enabled, the Zephyr RTOS shall restrict each thread to run on a single assigned CPU.
<<<
RELATIONS:
- TYPE: Parent
  VALUE: ZEP-SYRS-12

[REQUIREMENT]
UID: ZEP-SRS-34-16
STATUS: Draft
TYPE: Functional
COMPONENT: Multi Core
TITLE: Selective inter-processor reschedule signaling
STATEMENT: >>>
Where optimized inter-processor reschedule signaling is enabled, when a thread becomes ready to run the Zephyr RTOS shall signal only those CPUs that need to reschedule in response.
<<<
RELATIONS:
- TYPE: Parent
  VALUE: ZEP-SYRS-11

[REQUIREMENT]
UID: ZEP-SRS-34-17
STATUS: Draft
TYPE: Functional
COMPONENT: Multi Core
TITLE: Directed inter-processor reschedule signaling
STATEMENT: >>>
Where the architecture supports directed inter-processor interrupts, the Zephyr RTOS shall send a reschedule signal to a specific target CPU instead of broadcasting it to all other CPUs.
<<<
RELATIONS:
- TYPE: Parent
  VALUE: ZEP-SYRS-11

[REQUIREMENT]
UID: ZEP-SRS-34-18
STATUS: Draft
TYPE: Functional
COMPONENT: Multi Core
TITLE: Reschedule signaling for affinity-constrained threads
STATEMENT: >>>
When a thread restricted by its CPU affinity to a subset of CPUs preempts a thread on one CPU, the Zephyr RTOS shall issue the additional reschedule signals needed for the highest-priority runnable threads to be selected across all CPUs.
<<<
RELATIONS:
- TYPE: Parent
  VALUE: ZEP-SYRS-11

[REQUIREMENT]
UID: ZEP-SRS-34-19
STATUS: Draft
TYPE: Functional
COMPONENT: Multi Core
TITLE: Coherent memory for shared kernel data
STATEMENT: >>>
Where coherent memory placement is enabled on a cache-incoherent multiprocessor, the Zephyr RTOS shall place shared kernel data in cache-coherent memory.
<<<
RELATIONS:
- TYPE: Parent
  VALUE: ZEP-SYRS-11
