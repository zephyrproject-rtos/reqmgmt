[DOCUMENT]
TITLE: Data Passing
REQ_PREFIX: ZEP-SRS-15-

[GRAMMAR]
IMPORT_FROM_FILE: software_requirements.sgra

[TEXT]
STATEMENT: >>>
SPDX-License-Identifier: Apache-2.0
<<<

[TEXT]
STATEMENT: >>>
Data passing comprises the kernel objects that allow data to be exchanged
between threads, and between threads and interrupt service routines.

The Zephyr RTOS provides several data passing objects, each specified in its
own requirements document:

- Queues
- FIFOs
- LIFOs
- Stacks
- Message Queues (see Thread Communication)
- Mailboxes
- Pipes (see Thread Communication)
<<<
