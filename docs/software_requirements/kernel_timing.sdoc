[DOCUMENT]
TITLE: Kernel Timing
REQ_PREFIX: ZEP-SRS-28-

[GRAMMAR]
IMPORT_FROM_FILE: software_requirements.sgra

[TEXT]
STATEMENT: >>>
SPDX-License-Identifier: Apache-2.0
<<<

[[SECTION]]
TITLE: System Uptime

[REQUIREMENT]
UID: ZEP-SRS-28-1
STATUS: Draft
TYPE: Functional
COMPONENT: Kernel Timing
TITLE: System uptime in milliseconds
STATEMENT: >>>
The Zephyr RTOS shall provide a mechanism to obtain the time elapsed since the system booted, expressed in milliseconds.
<<<
RELATIONS:
- TYPE: Parent
  VALUE: ZEP-SYRS-28

[REQUIREMENT]
UID: ZEP-SRS-28-2
STATUS: Draft
TYPE: Functional
COMPONENT: Kernel Timing
TITLE: System uptime in system ticks
STATEMENT: >>>
The Zephyr RTOS shall provide a mechanism to obtain the time elapsed since the system booted, expressed in system ticks.
<<<
RELATIONS:
- TYPE: Parent
  VALUE: ZEP-SYRS-28

[REQUIREMENT]
UID: ZEP-SRS-28-3
STATUS: Draft
TYPE: Functional
COMPONENT: Kernel Timing
TITLE: System uptime in seconds
STATEMENT: >>>
The Zephyr RTOS shall provide a mechanism to obtain the time elapsed since the system booted, expressed in seconds.
<<<
RELATIONS:
- TYPE: Parent
  VALUE: ZEP-SYRS-28

[REQUIREMENT]
UID: ZEP-SRS-28-4
STATUS: Draft
TYPE: Functional
COMPONENT: Kernel Timing
TITLE: Elapsed time relative to a reference
STATEMENT: >>>
The Zephyr RTOS shall provide a mechanism to obtain the time elapsed, in milliseconds, since a caller-provided reference time, and to replace that reference time with the current system uptime.
<<<
RELATIONS:
- TYPE: Parent
  VALUE: ZEP-SYRS-28

[[/SECTION]]

[[SECTION]]
TITLE: Hardware Clock

[REQUIREMENT]
UID: ZEP-SRS-28-5
STATUS: Draft
TYPE: Functional
COMPONENT: Kernel Timing
TITLE: Hardware clock cycle count
STATEMENT: >>>
The Zephyr RTOS shall provide a mechanism to read the current value of the system's hardware clock as a 32-bit cycle count.
<<<
RELATIONS:
- TYPE: Parent
  VALUE: ZEP-SYRS-28

[REQUIREMENT]
UID: ZEP-SRS-28-6
STATUS: Draft
TYPE: Functional
COMPONENT: Kernel Timing
TITLE: 64-bit hardware clock cycle count
STATEMENT: >>>
The Zephyr RTOS shall provide a mechanism to read the current value of the system's hardware clock as a 64-bit cycle count.
<<<
RELATIONS:
- TYPE: Parent
  VALUE: ZEP-SYRS-28

[[/SECTION]]

[[SECTION]]
TITLE: Time Unit Conversion

[REQUIREMENT]
UID: ZEP-SRS-28-7
STATUS: Draft
TYPE: Functional
COMPONENT: Kernel Timing
TITLE: Conversion between time units
STATEMENT: >>>
The Zephyr RTOS shall provide a mechanism to convert time values between milliseconds, microseconds, nanoseconds, system ticks, and hardware cycles.
<<<
RELATIONS:
- TYPE: Parent
  VALUE: ZEP-SYRS-28

[[/SECTION]]

[[SECTION]]
TITLE: Thread Sleeping

[REQUIREMENT]
UID: ZEP-SRS-28-8
STATUS: Draft
TYPE: Functional
COMPONENT: Kernel Timing
TITLE: Suspending a thread for a duration
STATEMENT: >>>
The Zephyr RTOS shall provide a mechanism to suspend the execution of the calling thread for a specified duration, where the duration may be expressed in milliseconds, microseconds, nanoseconds, system ticks, or hardware cycles.
<<<
RELATIONS:
- TYPE: Parent
  VALUE: ZEP-SYRS-34

[REQUIREMENT]
UID: ZEP-SRS-28-9
STATUS: Draft
TYPE: Functional
COMPONENT: Kernel Timing
TITLE: Suspending a thread with microsecond resolution
STATEMENT: >>>
The Zephyr RTOS shall provide a mechanism to suspend the execution of the calling thread for a duration specified in microseconds.
<<<
RELATIONS:
- TYPE: Parent
  VALUE: ZEP-SYRS-34

[REQUIREMENT]
UID: ZEP-SRS-28-10
STATUS: Draft
TYPE: Functional
COMPONENT: Kernel Timing
TITLE: Thread readiness after sleep
STATEMENT: >>>
When the duration for which a thread was suspended elapses, the Zephyr RTOS shall make the thread eligible for execution again.
<<<
RELATIONS:
- TYPE: Parent
  VALUE: ZEP-SYRS-34

[REQUIREMENT]
UID: ZEP-SRS-28-11
STATUS: Draft
TYPE: Functional
COMPONENT: Kernel Timing
TITLE: Waking a sleeping thread
STATEMENT: >>>
The Zephyr RTOS shall provide a mechanism to prematurely wake a thread that is suspended for a duration.
<<<
RELATIONS:
- TYPE: Parent
  VALUE: ZEP-SYRS-34

[REQUIREMENT]
UID: ZEP-SRS-28-12
STATUS: Draft
TYPE: Functional
COMPONENT: Kernel Timing
TITLE: Reporting remaining time on premature wake
STATEMENT: >>>
When a thread suspended for a specified duration is woken before that duration has elapsed, the Zephyr RTOS shall report the amount of time that was remaining, expressed in milliseconds.
<<<
RELATIONS:
- TYPE: Parent
  VALUE: ZEP-SYRS-34

[REQUIREMENT]
UID: ZEP-SRS-28-15
STATUS: Draft
TYPE: Functional
COMPONENT: Kernel Timing
TITLE: Reporting remaining time on premature wake with microsecond resolution
STATEMENT: >>>
When a thread suspended for a duration specified in microseconds is woken before that duration has elapsed, the Zephyr RTOS shall report the amount of time that was remaining, expressed in microseconds.
<<<
RELATIONS:
- TYPE: Parent
  VALUE: ZEP-SYRS-34

[REQUIREMENT]
UID: ZEP-SRS-28-13
STATUS: Draft
TYPE: Functional
COMPONENT: Kernel Timing
TITLE: Busy waiting
STATEMENT: >>>
The Zephyr RTOS shall provide a mechanism for the calling thread to busy wait for a specified number of microseconds without relinquishing the CPU.
<<<
RELATIONS:
- TYPE: Parent
  VALUE: ZEP-SYRS-34

[[/SECTION]]

[[SECTION]]
TITLE: Timeouts

[REQUIREMENT]
UID: ZEP-SRS-28-14
STATUS: Draft
TYPE: Functional
COMPONENT: Kernel Timing
TITLE: Absolute timeouts
STATEMENT: >>>
Where 64-bit timeouts are enabled, the Zephyr RTOS shall accept timeouts specified as an absolute point in time, in addition to timeouts specified as a relative duration.
<<<
RELATIONS:
- TYPE: Parent
  VALUE: ZEP-SYRS-35

[[/SECTION]]

[REQUIREMENT]
UID: ZEP-SRS-28-16
STATUS: Draft
TYPE: Functional
COMPONENT: Kernel Timing
TITLE: Suspension duration rounding
STATEMENT: >>>
When converting a requested suspension duration to system ticks, the Zephyr RTOS
shall round up to the next tick boundary, so that the suspension is never shorter
than the requested duration.
<<<
RELATIONS:
- TYPE: Parent
  VALUE: ZEP-SYRS-34

[REQUIREMENT]
UID: ZEP-SRS-28-17
STATUS: Draft
TYPE: Functional
COMPONENT: Kernel Timing
TITLE: Suspension duration saturation
STATEMENT: >>>
When a requested suspension duration exceeds the representable timeout range, the
Zephyr RTOS shall saturate the timeout at the maximum representable value.
<<<
RELATIONS:
- TYPE: Parent
  VALUE: ZEP-SYRS-34

[REQUIREMENT]
UID: ZEP-SRS-28-18
STATUS: Draft
TYPE: Functional
COMPONENT: Kernel Timing
TITLE: Absolute timeout sequences without drift
STATEMENT: >>>
Where absolute timeouts are used for a sequence of suspensions, the Zephyr RTOS
shall not accumulate rounding drift across the sequence.
<<<
RELATIONS:
- TYPE: Parent
  VALUE: ZEP-SYRS-34

[REQUIREMENT]
UID: ZEP-SRS-28-19
STATUS: Draft
TYPE: Functional
COMPONENT: Kernel Timing
TITLE: Suspension during system initialization
STATEMENT: >>>
During system initialization after the kernel scheduler has started, the Zephyr
RTOS shall support suspending the calling context for a requested duration.
<<<
RELATIONS:
- TYPE: Parent
  VALUE: ZEP-SYRS-34

[REQUIREMENT]
UID: ZEP-SRS-28-20
STATUS: Draft
TYPE: Functional
COMPONENT: Kernel Timing
TITLE: Timeout expiry ordering
STATEMENT: >>>
When multiple timeouts are pending, the Zephyr RTOS shall process them in the
order of their expiry times, regardless of the order in which they were scheduled.
<<<
RELATIONS:
- TYPE: Parent
  VALUE: ZEP-SYRS-34
