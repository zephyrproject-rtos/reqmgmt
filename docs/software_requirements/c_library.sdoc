[DOCUMENT]
TITLE: C library
REQ_PREFIX: ZEP-SRS-18-

[GRAMMAR]
IMPORT_FROM_FILE: software_requirements.sgra

[TEXT]
STATEMENT: >>>
SPDX-License-Identifier: Apache-2.0
<<<

[REQUIREMENT]
UID: ZEP-SRS-18-1
STATUS: Draft
TYPE: Functional
COMPONENT: C Library
TITLE: Formatted output
STATEMENT: >>>
The Zephyr RTOS shall support formatted output.
<<<
USER_STORY: >>>
As a Zephyr RTOS user, I want to be able to printf with various output formats.
<<<
RELATIONS:
- TYPE: Parent
  VALUE: ZEP-SYRS-3

[REQUIREMENT]
UID: ZEP-SRS-18-2
STATUS: Draft
TYPE: Functional
COMPONENT: C Library
TITLE: Floating Point Math Support
STATEMENT: >>>
The Zephyr RTOS shall support floating point math libraries for processors where floating point is available.
<<<
USER_STORY: >>>
As a Zephyr RTOS user, I want to be able to calculate with floating point numbers.
<<<
RELATIONS:
- TYPE: Parent
  VALUE: ZEP-SYRS-3

[REQUIREMENT]
UID: ZEP-SRS-18-3
STATUS: Draft
TYPE: Functional
COMPONENT: C Library
TITLE: Boolean Primitives Support
STATEMENT: >>>
The Zephyr RTOS shall support boolean primitives.
<<<
USER_STORY: >>>
As a Zephyr RTOS user, I want to be able to work with boolean values and logic.
<<<
RELATIONS:
- TYPE: Parent
  VALUE: ZEP-SYRS-3

[REQUIREMENT]
UID: ZEP-SRS-18-4
STATUS: Draft
TYPE: Functional
COMPONENT: C Library
TITLE: Standard Unix time interface
STATEMENT: >>>
The Zephyr RTOS shall support the standard UNIX time interface.
<<<
USER_STORY: >>>
As a Zephyr User, I want to be able to use system time.
<<<
RELATIONS:
- TYPE: Parent
  VALUE: ZEP-SYRS-3

[REQUIREMENT]
UID: ZEP-SRS-18-5
STATUS: Draft
TYPE: Functional
COMPONENT: C Library
TITLE: Strings support
STATEMENT: >>>
The Zephyr RTOS shall support an interface to manage strings.
<<<
USER_STORY: >>>
As a Zephyr RTOS user, I want to be able to manipulate text strings.
<<<
RELATIONS:
- TYPE: Parent
  VALUE: ZEP-SYRS-3

[REQUIREMENT]
UID: ZEP-SRS-18-6
STATUS: Draft
TYPE: Functional
COMPONENT: C Library
TITLE: Moving/copying regions of memory
STATEMENT: >>>
The Zephyr RTOS shall support an interface to move contents between regions of memory.
<<<
USER_STORY: >>>
As a Zephyr RTOS user, I want to copy the memory contents to different addresses.
<<<
RELATIONS:
- TYPE: Parent
  VALUE: ZEP-SYRS-3

[REQUIREMENT]
UID: ZEP-SRS-18-7
STATUS: Draft
TYPE: Functional
COMPONENT: C Library
TITLE: I/O based interface
STATEMENT: >>>
The Zephyr RTOS shall support a file I/O based interface for driver communication.
<<<
USER_STORY: >>>
As a Zephyr RTOS user, I want to be able to use File I/O functions.
<<<
RELATIONS:
- TYPE: Parent
  VALUE: ZEP-SYRS-3

[REQUIREMENT]
UID: ZEP-SRS-18-8
STATUS: Draft
TYPE: Functional
COMPONENT: C Library
TITLE: C99 integer types
STATEMENT: >>>
The Zephyr RTOS shall support standard C99 integer types.
<<<
USER_STORY: >>>
As a Zephyr RTOS user, I want to be able to calculate with C99 Integers.
<<<
RELATIONS:
- TYPE: Parent
  VALUE: ZEP-SYRS-3

[REQUIREMENT]
UID: ZEP-SRS-18-9
STATUS: Draft
TYPE: Functional
COMPONENT: C Library
TITLE: Standard System Error Numbers (IEEE Std 1003.1-2017)
STATEMENT: >>>
The Zephyr RTOS shall support standard system error numbers as defined by IEEE Std 1003.1-2017.
<<<
USER_STORY: >>>
As a Zephyr RTOS user, I want to be able to use IEE Std 1003.1-2017 Error Numbers for Interoperability.
<<<
RELATIONS:
- TYPE: Parent
  VALUE: ZEP-SYRS-3

[REQUIREMENT]
UID: ZEP-SRS-18-10
STATUS: Draft
TYPE: Functional
COMPONENT: C Library
TITLE: Document set of Zephyr OS required C library functions in Safety Manual
STATEMENT: >>>
The set of C Library functions required by Zephyr shall be documented in the Zephyr Safety Manual.
<<<
USER_STORY: >>>
As a Zephyr user, I want to know which C library functions are being called by the Zephyr OS safety scope code.
<<<
RELATIONS:
- TYPE: Parent
  VALUE: ZEP-SYRS-3

[REQUIREMENT]
UID: ZEP-SRS-18-11
STATUS: Draft
TYPE: Functional
COMPONENT: C Library
TITLE: Support external C libraries documentation in Zephyr Safety Manual
STATEMENT: >>>
The Zephyr Safety Manual shall specify how to configure the support of external C Libraries.
<<<
USER_STORY: >>>
As a Zephyr User, I need to understand how to configure the external C libraries to align with the validation that has been performed.
<<<
RELATIONS:
- TYPE: Parent
  VALUE: ZEP-SYRS-3
