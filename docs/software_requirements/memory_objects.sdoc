[DOCUMENT]
TITLE: Memory Objects
REQ_PREFIX: ZEP-SRS-9-

[GRAMMAR]
IMPORT_FROM_FILE: software_requirements.sgra

[TEXT]
STATEMENT: >>>
SPDX-License-Identifier: Apache-2.0
<<<

[REQUIREMENT]
UID: ZEP-SRS-9-1
STATUS: Draft
TYPE: Functional
COMPONENT: Memory Objects
TITLE: Dynamic Memory Allocation
STATEMENT: >>>
The Zephyr RTOS shall allow threads to dynamically allocate variable-sized memory regions from a specified range of memory.
<<<
USER_STORY: >>>
As a Zephyr RTOS user I want my application to be able to dynamically allocate memory of a application defined size.
<<<
RELATIONS:
- TYPE: Parent
  VALUE: ZEP-SYRS-9

[REQUIREMENT]
UID: ZEP-SRS-9-2
STATUS: Draft
TYPE: Functional
COMPONENT: Memory Objects
TITLE: Memory Slab Object
STATEMENT: >>>
The Zephyr RTOS shall allow threads to dynamically allocate fixed-sized memory regions from a specified range of memory.
<<<
USER_STORY: >>>
As a Zephyr RTOS user I want a most efficient and least fragmentation prone dynamic memory allocation mechanism.
<<<
RELATIONS:
- TYPE: Parent
  VALUE: ZEP-SYRS-9

[REQUIREMENT]
UID: ZEP-SRS-9-3
STATUS: Draft
TYPE: Functional
COMPONENT: Memory Objects
TITLE: Heap definition at compile time
STATEMENT: >>>
The Zephyr RTOS shall provide a mechanism to define and initialize a memory heap at compile time.
<<<
RELATIONS:
- TYPE: Parent
  VALUE: ZEP-SYRS-9

[REQUIREMENT]
UID: ZEP-SRS-9-4
STATUS: Draft
TYPE: Functional
COMPONENT: Memory Objects
TITLE: Heap initialization at run time
STATEMENT: >>>
The Zephyr RTOS shall provide a mechanism to initialize a memory heap at run time over a caller-provided memory region.
<<<
RELATIONS:
- TYPE: Parent
  VALUE: ZEP-SYRS-9

[REQUIREMENT]
UID: ZEP-SRS-9-5
STATUS: Draft
TYPE: Functional
COMPONENT: Memory Objects
TITLE: Heap allocation
STATEMENT: >>>
The Zephyr RTOS shall provide a mechanism to allocate a block of memory of a requested size from a heap.
<<<
RELATIONS:
- TYPE: Parent
  VALUE: ZEP-SYRS-9

[REQUIREMENT]
UID: ZEP-SRS-9-6
STATUS: Draft
TYPE: Functional
COMPONENT: Memory Objects
TITLE: Heap aligned allocation
STATEMENT: >>>
The Zephyr RTOS shall provide a mechanism to allocate a block of memory from a heap with a requested alignment.
<<<
RELATIONS:
- TYPE: Parent
  VALUE: ZEP-SYRS-9

[REQUIREMENT]
UID: ZEP-SRS-9-7
STATUS: Draft
TYPE: Functional
COMPONENT: Memory Objects
TITLE: Heap allocation timeout
STATEMENT: >>>
When allocating memory from a heap, the Zephyr RTOS shall accept a timeout that specifies the maximum time to wait for sufficient memory to become available.
<<<
RELATIONS:
- TYPE: Parent
  VALUE: ZEP-SYRS-9

[REQUIREMENT]
UID: ZEP-SRS-9-8
STATUS: Draft
TYPE: Functional
COMPONENT: Memory Objects
TITLE: Heap allocation failure
STATEMENT: >>>
When sufficient memory cannot be allocated from a heap within the specified time, the Zephyr RTOS shall report that the allocation failed.
<<<
RELATIONS:
- TYPE: Parent
  VALUE: ZEP-SYRS-9

[REQUIREMENT]
UID: ZEP-SRS-9-9
STATUS: Draft
TYPE: Functional
COMPONENT: Memory Objects
TITLE: Heap reallocation
STATEMENT: >>>
The Zephyr RTOS shall provide a mechanism to resize a previously allocated heap block while preserving its contents up to the smaller of the old and new sizes.
<<<
RELATIONS:
- TYPE: Parent
  VALUE: ZEP-SYRS-9

[REQUIREMENT]
UID: ZEP-SRS-9-10
STATUS: Draft
TYPE: Functional
COMPONENT: Memory Objects
TITLE: Heap free
STATEMENT: >>>
The Zephyr RTOS shall provide a mechanism to release a previously allocated block of memory back to its heap.
<<<
RELATIONS:
- TYPE: Parent
  VALUE: ZEP-SYRS-9

[REQUIREMENT]
UID: ZEP-SRS-9-11
STATUS: Draft
TYPE: Functional
COMPONENT: Memory Objects
TITLE: System heap allocation and release
STATEMENT: >>>
The Zephyr RTOS shall provide a mechanism to allocate memory from and release memory to a shared system heap.
<<<
RELATIONS:
- TYPE: Parent
  VALUE: ZEP-SYRS-9

[REQUIREMENT]
UID: ZEP-SRS-9-12
STATUS: Draft
TYPE: Functional
COMPONENT: Memory Objects
TITLE: Memory slab definition at compile time
STATEMENT: >>>
The Zephyr RTOS shall provide a mechanism to define and initialize a memory slab of fixed-size blocks at compile time.
<<<
RELATIONS:
- TYPE: Parent
  VALUE: ZEP-SYRS-9

[REQUIREMENT]
UID: ZEP-SRS-9-13
STATUS: Draft
TYPE: Functional
COMPONENT: Memory Objects
TITLE: Memory slab initialization at run time
STATEMENT: >>>
The Zephyr RTOS shall provide a mechanism to initialize a memory slab at run time over a caller-provided memory region.
<<<
RELATIONS:
- TYPE: Parent
  VALUE: ZEP-SYRS-9

[REQUIREMENT]
UID: ZEP-SRS-9-14
STATUS: Draft
TYPE: Functional
COMPONENT: Memory Objects
TITLE: Memory slab block allocation
STATEMENT: >>>
The Zephyr RTOS shall provide a mechanism to allocate a fixed-size block from a memory slab, accepting a timeout that specifies the maximum time to wait for a free block.
<<<
RELATIONS:
- TYPE: Parent
  VALUE: ZEP-SYRS-9

[REQUIREMENT]
UID: ZEP-SRS-9-15
STATUS: Draft
TYPE: Functional
COMPONENT: Memory Objects
TITLE: Memory slab allocation timeout expiry
STATEMENT: >>>
When no block becomes available in a memory slab within the specified time, the Zephyr RTOS shall return an error indicating that no block was allocated.
<<<
RELATIONS:
- TYPE: Parent
  VALUE: ZEP-SYRS-9

[REQUIREMENT]
UID: ZEP-SRS-9-16
STATUS: Draft
TYPE: Functional
COMPONENT: Memory Objects
TITLE: Memory slab block free
STATEMENT: >>>
The Zephyr RTOS shall provide a mechanism to release a previously allocated block back to its memory slab.
<<<
RELATIONS:
- TYPE: Parent
  VALUE: ZEP-SYRS-9

[REQUIREMENT]
UID: ZEP-SRS-9-17
STATUS: Draft
TYPE: Functional
COMPONENT: Memory Objects
TITLE: Memory slab usage statistics
STATEMENT: >>>
The Zephyr RTOS shall provide a mechanism to query the number of used and free blocks in a memory slab.
<<<
RELATIONS:
- TYPE: Parent
  VALUE: ZEP-SYRS-9

[REQUIREMENT]
UID: ZEP-SRS-9-18
STATUS: Draft
TYPE: Functional
COMPONENT: Memory Objects
TITLE: Enumerating defined heaps
STATEMENT: >>>
The Zephyr RTOS shall provide a mechanism to obtain the set of heaps that were defined at compile time.
<<<
RELATIONS:
- TYPE: Parent
  VALUE: ZEP-SYRS-9

[REQUIREMENT]
UID: ZEP-SRS-9-19
STATUS: Draft
TYPE: Functional
COMPONENT: Memory Objects
TITLE: Heap usage statistics
STATEMENT: >>>
Where heap runtime statistics are enabled, the Zephyr RTOS shall provide a mechanism to query the amounts of currently allocated and free memory in a heap and the maximum amount of memory that has been allocated from it.
<<<
RELATIONS:
- TYPE: Parent
  VALUE: ZEP-SYRS-9

[REQUIREMENT]
UID: ZEP-SRS-9-20
STATUS: Draft
TYPE: Functional
COMPONENT: Memory Objects
TITLE: Resetting the heap allocation maximum
STATEMENT: >>>
Where heap runtime statistics are enabled, the Zephyr RTOS shall provide a mechanism to reset the recorded maximum amount of allocated memory of a heap to the amount currently allocated.
<<<
RELATIONS:
- TYPE: Parent
  VALUE: ZEP-SYRS-9

[REQUIREMENT]
UID: ZEP-SRS-9-21
STATUS: Draft
TYPE: Functional
COMPONENT: Memory Objects
TITLE: Largest allocatable block
STATEMENT: >>>
Where heap runtime statistics are enabled, the Zephyr RTOS shall provide a mechanism to query the size of the largest block that can currently be allocated from a heap.
<<<
RELATIONS:
- TYPE: Parent
  VALUE: ZEP-SYRS-9

[REQUIREMENT]
UID: ZEP-SRS-9-22
STATUS: Draft
TYPE: Functional
COMPONENT: Memory Objects
TITLE: Allocated heap block usable size
STATEMENT: >>>
The Zephyr RTOS shall provide a mechanism to query the usable size of an allocated heap block.
<<<
RELATIONS:
- TYPE: Parent
  VALUE: ZEP-SYRS-9

[REQUIREMENT]
UID: ZEP-SRS-9-23
STATUS: Draft
TYPE: Functional
COMPONENT: Memory Objects
TITLE: Registering a heap event listener
STATEMENT: >>>
Where heap event notification is enabled, the Zephyr RTOS shall provide a mechanism to register a listener for the memory events of a designated heap.
<<<
RELATIONS:
- TYPE: Parent
  VALUE: ZEP-SYRS-9

[REQUIREMENT]
UID: ZEP-SRS-9-24
STATUS: Draft
TYPE: Functional
COMPONENT: Memory Objects
TITLE: Unregistering a heap event listener
STATEMENT: >>>
Where heap event notification is enabled, the Zephyr RTOS shall provide a mechanism to unregister a previously registered heap event listener.
<<<
RELATIONS:
- TYPE: Parent
  VALUE: ZEP-SYRS-9

[REQUIREMENT]
UID: ZEP-SRS-9-25
STATUS: Draft
TYPE: Functional
COMPONENT: Memory Objects
TITLE: Heap event notification
STATEMENT: >>>
When memory is allocated from, released to, or resized within a heap for which a listener is registered, the Zephyr RTOS shall notify the registered listeners of the event.
<<<
RELATIONS:
- TYPE: Parent
  VALUE: ZEP-SYRS-9

[REQUIREMENT]
UID: ZEP-SRS-9-26
STATUS: Draft
TYPE: Functional
COMPONENT: Memory Objects
TITLE: Double free detection
STATEMENT: >>>
Where heap hardening is enabled, the Zephyr RTOS shall detect the release of a heap block that is not currently allocated.
<<<
RELATIONS:
- TYPE: Parent
  VALUE: ZEP-SYRS-9

[REQUIREMENT]
UID: ZEP-SRS-9-27
STATUS: Draft
TYPE: Functional
COMPONENT: Memory Objects
TITLE: Heap metadata corruption detection
STATEMENT: >>>
Where heap hardening is enabled, the Zephyr RTOS shall detect corruption of heap metadata during allocation and release operations.
<<<
RELATIONS:
- TYPE: Parent
  VALUE: ZEP-SYRS-9

[REQUIREMENT]
UID: ZEP-SRS-9-28
STATUS: Draft
TYPE: Functional
COMPONENT: Memory Objects
TITLE: Heap block overflow detection
STATEMENT: >>>
Where heap canaries are enabled, the Zephyr RTOS shall detect writes beyond the end of an allocated heap block when the block is released or resized.
<<<
RELATIONS:
- TYPE: Parent
  VALUE: ZEP-SYRS-9

[REQUIREMENT]
UID: ZEP-SRS-9-29
STATUS: Draft
TYPE: Functional
COMPONENT: Memory Objects
TITLE: Heap corruption response
STATEMENT: >>>
If heap corruption is detected, then the Zephyr RTOS shall report a fatal error.
<<<
RELATIONS:
- TYPE: Parent
  VALUE: ZEP-SYRS-9
