[DOCUMENT]
TITLE: File system
REQ_PREFIX: ZEP-SRS-17-

[GRAMMAR]
IMPORT_FROM_FILE: software_requirements.sgra

[TEXT]
STATEMENT: >>>
SPDX-License-Identifier: Apache-2.0
<<<

[REQUIREMENT]
UID: ZEP-SRS-17-1
STATUS: Draft
TYPE: Functional
COMPONENT: File System
TITLE: Create file
STATEMENT: >>>
Zephyr shall provide file create capabilities for files on the file system.
<<<
USER_STORY: >>>
As a Zephyr OS user I want to be able to create a new file or overwrite an existing file at the same filesystem location / identifier (e.g. path + name).
<<<
RELATIONS:
- TYPE: Parent
  VALUE: ZEP-SYRS-6

[REQUIREMENT]
UID: ZEP-SRS-17-2
STATUS: Draft
TYPE: Functional
COMPONENT: File System
TITLE: Open files
STATEMENT: >>>
Zephyr shall provide file open capabilities for files on the file system.
<<<
USER_STORY: >>>
As a Zephyr OS user I want to be able to open a file for writing or reading.
When opened for writing, I want to have exclusive access to the file.
<<<
RELATIONS:
- TYPE: Parent
  VALUE: ZEP-SYRS-6

[REQUIREMENT]
UID: ZEP-SRS-17-3
STATUS: Draft
TYPE: Functional
COMPONENT: File System
TITLE: Read files
STATEMENT: >>>
Zephyr shall provide read access to files in the file system.
<<<
USER_STORY: >>>
As a Zephyr OS user I want to be able to read from an existing file, also while the file is read from multiple and write accessed from one other instances.
<<<
RELATIONS:
- TYPE: Parent
  VALUE: ZEP-SYRS-6

[REQUIREMENT]
UID: ZEP-SRS-17-4
STATUS: Draft
TYPE: Functional
COMPONENT: File System
TITLE: Write to files
STATEMENT: >>>
Zephyr shall provide write access to the files in the file system.
<<<
USER_STORY: >>>
As a Zephyr OS user I want to be able to write to a file either from the beginning of the file or appending at the end.
<<<
RELATIONS:
- TYPE: Parent
  VALUE: ZEP-SYRS-6

[REQUIREMENT]
UID: ZEP-SRS-17-5
STATUS: Draft
TYPE: Functional
COMPONENT: File System
TITLE: Close file
STATEMENT: >>>
Zephyr shall provide file close capabilities for files on the file system.
<<<
USER_STORY: >>>
As a Zephyr OS user I want to be able to close a file after being finished with my file operations, unlocking any access restrictions.
<<<
RELATIONS:
- TYPE: Parent
  VALUE: ZEP-SYRS-6

[REQUIREMENT]
UID: ZEP-SRS-17-6
STATUS: Draft
TYPE: Functional
COMPONENT: File System
TITLE: Move file
STATEMENT: >>>
Zephyr shall provide the capability to move files on the file system.
<<<
RELATIONS:
- TYPE: Parent
  VALUE: ZEP-SYRS-6

[REQUIREMENT]
UID: ZEP-SRS-17-7
STATUS: Draft
TYPE: Functional
COMPONENT: File System
TITLE: Delete file
STATEMENT: >>>
Zephyr shall provide file delete capabilities for files on the file system.
<<<
USER_STORY: >>>
As a Zephyr OS user I want to be able to delete an existing file.
<<<
RELATIONS:
- TYPE: Parent
  VALUE: ZEP-SYRS-6

[REQUIREMENT]
UID: ZEP-SRS-17-8
STATUS: Draft
TYPE: Functional
COMPONENT: File System
TITLE: Seek within a file
STATEMENT: >>>
The Zephyr RTOS shall provide a mechanism to change the read/write position within an open file.
<<<
RELATIONS:
- TYPE: Parent
  VALUE: ZEP-SYRS-6

[REQUIREMENT]
UID: ZEP-SRS-17-9
STATUS: Draft
TYPE: Functional
COMPONENT: File System
TITLE: Query file position
STATEMENT: >>>
The Zephyr RTOS shall provide a mechanism to obtain the current read/write position within an open file.
<<<
RELATIONS:
- TYPE: Parent
  VALUE: ZEP-SYRS-6

[REQUIREMENT]
UID: ZEP-SRS-17-10
STATUS: Draft
TYPE: Functional
COMPONENT: File System
TITLE: Truncate a file
STATEMENT: >>>
The Zephyr RTOS shall provide a mechanism to change the size of an open file.
<<<
RELATIONS:
- TYPE: Parent
  VALUE: ZEP-SYRS-6

[REQUIREMENT]
UID: ZEP-SRS-17-11
STATUS: Draft
TYPE: Functional
COMPONENT: File System
TITLE: Synchronize a file
STATEMENT: >>>
The Zephyr RTOS shall provide a mechanism to flush cached data of an open file to the underlying storage.
<<<
RELATIONS:
- TYPE: Parent
  VALUE: ZEP-SYRS-6

[REQUIREMENT]
UID: ZEP-SRS-17-12
STATUS: Draft
TYPE: Functional
COMPONENT: File System
TITLE: Create a directory
STATEMENT: >>>
The Zephyr RTOS shall provide a mechanism to create a directory on the file system.
<<<
RELATIONS:
- TYPE: Parent
  VALUE: ZEP-SYRS-6

[REQUIREMENT]
UID: ZEP-SRS-17-13
STATUS: Draft
TYPE: Functional
COMPONENT: File System
TITLE: Open a directory
STATEMENT: >>>
The Zephyr RTOS shall provide a mechanism to open a directory for reading its entries.
<<<
RELATIONS:
- TYPE: Parent
  VALUE: ZEP-SYRS-6

[REQUIREMENT]
UID: ZEP-SRS-17-14
STATUS: Draft
TYPE: Functional
COMPONENT: File System
TITLE: Read directory entries
STATEMENT: >>>
The Zephyr RTOS shall provide a mechanism to read the entries of an open directory.
<<<
RELATIONS:
- TYPE: Parent
  VALUE: ZEP-SYRS-6

[REQUIREMENT]
UID: ZEP-SRS-17-15
STATUS: Draft
TYPE: Functional
COMPONENT: File System
TITLE: Close a directory
STATEMENT: >>>
The Zephyr RTOS shall provide a mechanism to close an open directory.
<<<
RELATIONS:
- TYPE: Parent
  VALUE: ZEP-SYRS-6

[REQUIREMENT]
UID: ZEP-SRS-17-16
STATUS: Draft
TYPE: Functional
COMPONENT: File System
TITLE: Query file or directory status
STATEMENT: >>>
The Zephyr RTOS shall provide a mechanism to obtain status information about a file or directory.
<<<
RELATIONS:
- TYPE: Parent
  VALUE: ZEP-SYRS-6

[REQUIREMENT]
UID: ZEP-SRS-17-17
STATUS: Draft
TYPE: Functional
COMPONENT: File System
TITLE: Query file system volume statistics
STATEMENT: >>>
The Zephyr RTOS shall provide a mechanism to obtain statistics about a mounted file system volume.
<<<
RELATIONS:
- TYPE: Parent
  VALUE: ZEP-SYRS-6

[REQUIREMENT]
UID: ZEP-SRS-17-18
STATUS: Draft
TYPE: Functional
COMPONENT: File System
TITLE: Mount a file system
STATEMENT: >>>
The Zephyr RTOS shall provide a mechanism to mount a file system at a specified mount point.
<<<
RELATIONS:
- TYPE: Parent
  VALUE: ZEP-SYRS-6

[REQUIREMENT]
UID: ZEP-SRS-17-19
STATUS: Draft
TYPE: Functional
COMPONENT: File System
TITLE: Unmount a file system
STATEMENT: >>>
The Zephyr RTOS shall provide a mechanism to unmount a mounted file system.
<<<
RELATIONS:
- TYPE: Parent
  VALUE: ZEP-SYRS-6

[REQUIREMENT]
UID: ZEP-SRS-17-20
STATUS: Draft
TYPE: Functional
COMPONENT: File System
TITLE: Register a file system type
STATEMENT: >>>
The Zephyr RTOS shall provide a mechanism to register and unregister a file system implementation.
<<<
RELATIONS:
- TYPE: Parent
  VALUE: ZEP-SYRS-6
