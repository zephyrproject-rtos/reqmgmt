[DOCUMENT]
TITLE: Thread Scheduling
REQ_PREFIX: ZEP-SRS-2-

[GRAMMAR]
IMPORT_FROM_FILE: software_requirements.sgra

[TEXT]
STATEMENT: >>>
SPDX-License-Identifier: Apache-2.0
<<<

[[SECTION]]
TITLE: Thread Scheduling

[REQUIREMENT]
UID: ZEP-SRS-2-4
STATUS: Draft
TYPE: Functional
COMPONENT: Thread Scheduling
TITLE: Scheduling a thread based on an event
STATEMENT: >>>
When an event on which a thread is waiting occurs, the Zephyr RTOS shall make the waiting thread ready.
<<<
USER_STORY: >>>
As a Zephyr RTOS user, I want to be able to execute work which reacts on events and interrupts the current executed work.
<<<
RELATIONS:
- TYPE: Parent
  VALUE: ZEP-SYRS-15

[REQUIREMENT]
UID: ZEP-SRS-2-5
STATUS: Draft
TYPE: Functional
COMPONENT: Thread Scheduling
TITLE: Deadline Scheduling Priorities
STATEMENT: >>>
Where earliest-deadline-first scheduling is enabled, when two or more ready threads have equal static priority, the Zephyr RTOS shall consider the thread with the earliest deadline to have the higher priority.
<<<
USER_STORY: >>>
As a Zephyr RTOS user, I want to be able to schedule threads by earliest deadline first.
<<<
RELATIONS:
- TYPE: Parent
  VALUE: ZEP-SYRS-17

[REQUIREMENT]
UID: ZEP-SRS-2-8
STATUS: Draft
TYPE: Functional
COMPONENT: Thread Scheduling
TITLE: Numeric thread priorities
STATEMENT: >>>
The Zephyr RTOS shall schedule threads according to a numeric thread priority, giving a thread with a numerically lower priority value precedence over a thread with a numerically higher priority value.
<<<
USER_STORY: >>>
As a Zephyr RTOS user, I want the OS to schedule threads by numeric priority so that I can control the relative importance of my threads.
<<<
RELATIONS:
- TYPE: Parent
  VALUE: ZEP-SYRS-17

[REQUIREMENT]
UID: ZEP-SRS-2-9
STATUS: Draft
TYPE: Functional
COMPONENT: Thread Scheduling
TITLE: Preemption support
STATEMENT: >>>
While the current thread is preemptible, when a thread of higher priority becomes ready, the Zephyr RTOS shall suspend execution of the current thread and select the higher-priority thread as the current thread.
<<<
USER_STORY: >>>
As a Zephyr RTOS user, I want a higher priority thread to take over the CPU as soon as it becomes ready, so that important work is not delayed by less important work.
<<<
RELATIONS:
- TYPE: Parent
  VALUE: ZEP-SYRS-17

[REQUIREMENT]
UID: ZEP-SRS-2-10
STATUS: Draft
TYPE: Functional
COMPONENT: Thread Scheduling
TITLE: Thread priority ranges
STATEMENT: >>>
The Zephyr RTOS shall partition the thread priority space into a cooperative priority range and a preemptible priority range.
<<<
USER_STORY: >>>
As a Zephyr RTOS user, I want thread priorities organized into cooperative and preemptible ranges, so that a thread's priority determines its preemption behavior.
<<<
RELATIONS:
- TYPE: Parent
  VALUE: ZEP-SYRS-17

[REQUIREMENT]
UID: ZEP-SRS-2-11
STATUS: Draft
TYPE: Functional
COMPONENT: Thread Scheduling
TITLE: Time sharing of CPU resources
STATEMENT: >>>
Where time slicing is enabled, the Zephyr RTOS shall cause the current preemptible thread to relinquish the CPU after not more than a configurable time slice period whenever one or more other ready threads of the same priority exist.
<<<
USER_STORY: >>>
As a Zephyr RTOS user, I want to be able to configure my RTOS in the way, that the CPU resources are shared evenly among executed threads of the same priority.
<<<
RELATIONS:
- TYPE: Parent
  VALUE: ZEP-SYRS-16

[[/SECTION]]
