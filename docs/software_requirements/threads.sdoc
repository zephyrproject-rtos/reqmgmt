[DOCUMENT]
TITLE: Threads
REQ_PREFIX: ZEP-SRS-1-

[GRAMMAR]
IMPORT_FROM_FILE: software_requirements.sgra

[TEXT]
STATEMENT: >>>
SPDX-License-Identifier: Apache-2.0
<<<

[REQUIREMENT]
UID: ZEP-SRS-1-1
STATUS: Draft
TYPE: Functional
COMPONENT: Threads
TITLE: Creating threads
STATEMENT: >>>
The Zephyr RTOS shall provide an interface to create a thread at run time.
<<<
RELATIONS:
- TYPE: Parent
  VALUE: ZEP-SYRS-15
- TYPE: Parent
  VALUE: ZEP-SYRS-16

[REQUIREMENT]
UID: ZEP-SRS-1-2
STATUS: Draft
TYPE: Functional
COMPONENT: Threads
TITLE: Setting thread priority
STATEMENT: >>>
The Zephyr RTOS shall provide an interface to set a thread's priority.
<<<
RELATIONS:
- TYPE: Parent
  VALUE: ZEP-SYRS-17

[REQUIREMENT]
UID: ZEP-SRS-1-3
STATUS: Draft
TYPE: Functional
COMPONENT: Threads
TITLE: Suspending a thread
STATEMENT: >>>
The Zephyr RTOS shall provide an interface to suspend a thread.
<<<
RELATIONS:
- TYPE: Parent
  VALUE: ZEP-SYRS-15
- TYPE: Parent
  VALUE: ZEP-SYRS-16

[REQUIREMENT]
UID: ZEP-SRS-1-4
STATUS: Draft
TYPE: Functional
COMPONENT: Threads
TITLE: Resuming a suspended thread
STATEMENT: >>>
The Zephyr RTOS shall provide an interface to resume a suspended thread.
<<<
RELATIONS:
- TYPE: Parent
  VALUE: ZEP-SYRS-15
- TYPE: Parent
  VALUE: ZEP-SYRS-16

[REQUIREMENT]
UID: ZEP-SRS-1-5
STATUS: Draft
TYPE: Functional
COMPONENT: Threads
TITLE: Delayed thread start
STATEMENT: >>>
When a thread is created, the Zephyr RTOS shall accept a scheduling delay after which the thread is started.
<<<
RELATIONS:
- TYPE: Parent
  VALUE: ZEP-SYRS-15
- TYPE: Parent
  VALUE: ZEP-SYRS-16

[REQUIREMENT]
UID: ZEP-SRS-1-6
STATUS: Draft
TYPE: Functional
COMPONENT: Threads
TITLE: Aborting a thread
STATEMENT: >>>
The Zephyr RTOS shall provide an interface to abort (terminate) a thread.
<<<
RELATIONS:
- TYPE: Parent
  VALUE: ZEP-SYRS-15
- TYPE: Parent
  VALUE: ZEP-SYRS-16

[REQUIREMENT]
UID: ZEP-SRS-1-7
STATUS: Draft
TYPE: Functional
COMPONENT: Threads
TITLE: Thread states
STATEMENT: >>>
The Zephyr RTOS shall maintain a state for each thread that reflects its position in the thread life cycle.
<<<
RELATIONS:
- TYPE: Parent
  VALUE: ZEP-SYRS-15
- TYPE: Parent
  VALUE: ZEP-SYRS-16

[REQUIREMENT]
UID: ZEP-SRS-1-8
STATUS: Draft
TYPE: Functional
COMPONENT: Threads
TITLE: Thread stack objects
STATEMENT: >>>
Each thread shall have its own dedicated stack.
<<<
RELATIONS:
- TYPE: Parent
  VALUE: ZEP-SYRS-15

[REQUIREMENT]
UID: ZEP-SRS-1-35
STATUS: Draft
TYPE: Functional
COMPONENT: Threads
TITLE: Defining a thread stack at compile time
STATEMENT: >>>
The Zephyr RTOS shall provide a mechanism to define a thread stack of a specified size at compile time.
<<<
RELATIONS:
- TYPE: Parent
  VALUE: ZEP-SYRS-15
- TYPE: Parent
  VALUE: ZEP-SYRS-16

[REQUIREMENT]
UID: ZEP-SRS-1-9
STATUS: Draft
TYPE: Functional
COMPONENT: Threads
TITLE: Thread privileges
STATEMENT: >>>
The Zephyr RTOS shall provide an interface to create threads with defined privilege.
<<<
RELATIONS:
- TYPE: Parent
  VALUE: ZEP-SYRS-15
- TYPE: Parent
  VALUE: ZEP-SYRS-16

[REQUIREMENT]
UID: ZEP-SRS-1-11
STATUS: Draft
TYPE: Functional
COMPONENT: Threads
TITLE: Thread Options
STATEMENT: >>>
When creating a thread, the Zephyr RTOS shall accept a set of thread options that modify how the kernel treats the thread.
<<<
RELATIONS:
- TYPE: Parent
  VALUE: ZEP-SYRS-15
- TYPE: Parent
  VALUE: ZEP-SYRS-16

[REQUIREMENT]
UID: ZEP-SRS-1-12
STATUS: Draft
TYPE: Functional
COMPONENT: Threads
TITLE: Thread Custom Data
STATEMENT: >>>
Every thread shall have a custom data area.
<<<
RELATIONS:
- TYPE: Parent
  VALUE: ZEP-SYRS-15
- TYPE: Parent
  VALUE: ZEP-SYRS-16

[REQUIREMENT]
UID: ZEP-SRS-1-13
STATUS: Draft
TYPE: Functional
COMPONENT: Threads
TITLE: Defining a thread at compile time
STATEMENT: >>>
The Zephyr RTOS shall provide an interface to define a thread at compile time.
<<<
RELATIONS:
- TYPE: Parent
  VALUE: ZEP-SYRS-15
- TYPE: Parent
  VALUE: ZEP-SYRS-16

[REQUIREMENT]
UID: ZEP-SRS-1-14
STATUS: Draft
TYPE: Functional
COMPONENT: Threads
TITLE: Starting an inactive thread
STATEMENT: >>>
The Zephyr RTOS shall provide an interface to start a thread that was created without being scheduled to start.
<<<
RELATIONS:
- TYPE: Parent
  VALUE: ZEP-SYRS-15
- TYPE: Parent
  VALUE: ZEP-SYRS-16

[REQUIREMENT]
UID: ZEP-SRS-1-15
STATUS: Draft
TYPE: Functional
COMPONENT: Threads
TITLE: Passing parameters to a thread entry point
STATEMENT: >>>
When a thread is created, the Zephyr RTOS shall pass a defined set of parameters to the thread's entry point function.
<<<
RELATIONS:
- TYPE: Parent
  VALUE: ZEP-SYRS-15
- TYPE: Parent
  VALUE: ZEP-SYRS-16

[REQUIREMENT]
UID: ZEP-SRS-1-16
STATUS: Draft
TYPE: Functional
COMPONENT: Threads
TITLE: Getting thread priority
STATEMENT: >>>
The Zephyr RTOS shall provide an interface to get a thread's priority.
<<<
RELATIONS:
- TYPE: Parent
  VALUE: ZEP-SYRS-17

[REQUIREMENT]
UID: ZEP-SRS-1-17
STATUS: Draft
TYPE: Functional
COMPONENT: Threads
TITLE: Assigning a thread name
STATEMENT: >>>
The Zephyr RTOS shall provide an interface to assign a name to a thread.
<<<
RELATIONS:
- TYPE: Parent
  VALUE: ZEP-SYRS-15
- TYPE: Parent
  VALUE: ZEP-SYRS-16

[REQUIREMENT]
UID: ZEP-SRS-1-18
STATUS: Draft
TYPE: Functional
COMPONENT: Threads
TITLE: Retrieving a thread name
STATEMENT: >>>
The Zephyr RTOS shall provide an interface to retrieve the name of a thread.
<<<
RELATIONS:
- TYPE: Parent
  VALUE: ZEP-SYRS-15
- TYPE: Parent
  VALUE: ZEP-SYRS-16

[REQUIREMENT]
UID: ZEP-SRS-1-19
STATUS: Draft
TYPE: Functional
COMPONENT: Threads
TITLE: Identifying the current thread
STATEMENT: >>>
The Zephyr RTOS shall provide an interface to identify the thread that is currently executing.
<<<
RELATIONS:
- TYPE: Parent
  VALUE: ZEP-SYRS-15
- TYPE: Parent
  VALUE: ZEP-SYRS-16

[REQUIREMENT]
UID: ZEP-SRS-1-20
STATUS: Draft
TYPE: Functional
COMPONENT: Threads
TITLE: Waiting for a thread to terminate
STATEMENT: >>>
The Zephyr RTOS shall provide an interface for a thread to wait until another thread has terminated, subject to a specified timeout.
<<<
RELATIONS:
- TYPE: Parent
  VALUE: ZEP-SYRS-15
- TYPE: Parent
  VALUE: ZEP-SYRS-16

[REQUIREMENT]
UID: ZEP-SRS-1-21
STATUS: Draft
TYPE: Functional
COMPONENT: Threads
TITLE: Querying a thread state
STATEMENT: >>>
The Zephyr RTOS shall provide an interface to obtain a human-readable representation of a thread's current state.
<<<
RELATIONS:
- TYPE: Parent
  VALUE: ZEP-SYRS-15
- TYPE: Parent
  VALUE: ZEP-SYRS-16

[REQUIREMENT]
UID: ZEP-SRS-1-22
STATUS: Draft
TYPE: Functional
COMPONENT: Threads
TITLE: Single-thread operation
STATEMENT: >>>
Where multithreading is disabled, the Zephyr RTOS shall execute the application as a single thread of control.
<<<
RELATIONS:
- TYPE: Parent
  VALUE: ZEP-SYRS-15

[REQUIREMENT]
UID: ZEP-SRS-1-23
STATUS: Draft
TYPE: Functional
COMPONENT: Threads
TITLE: Thread-local storage
STATEMENT: >>>
Where thread-local storage is enabled, the Zephyr RTOS shall give each thread its own instance of variables declared as thread-local.
<<<
RELATIONS:
- TYPE: Parent
  VALUE: ZEP-SYRS-15
- TYPE: Parent
  VALUE: ZEP-SYRS-16

[REQUIREMENT]
UID: ZEP-SRS-1-24
STATUS: Draft
TYPE: Functional
COMPONENT: Threads
TITLE: Allocating a thread stack at run time
STATEMENT: >>>
Where dynamic threads are enabled, the Zephyr RTOS shall provide a mechanism to allocate a thread stack at run time.
<<<
RELATIONS:
- TYPE: Parent
  VALUE: ZEP-SYRS-15
- TYPE: Parent
  VALUE: ZEP-SYRS-16

[REQUIREMENT]
UID: ZEP-SRS-1-25
STATUS: Draft
TYPE: Functional
COMPONENT: Threads
TITLE: Releasing a run-time allocated thread stack
STATEMENT: >>>
Where dynamic threads are enabled, the Zephyr RTOS shall provide a mechanism to release a thread stack that was allocated at run time.
<<<
RELATIONS:
- TYPE: Parent
  VALUE: ZEP-SYRS-15
- TYPE: Parent
  VALUE: ZEP-SYRS-16

[REQUIREMENT]
UID: ZEP-SRS-1-26
STATUS: Draft
TYPE: Functional
COMPONENT: Threads
TITLE: Iterating over threads
STATEMENT: >>>
Where thread monitoring is enabled, the Zephyr RTOS shall provide a mechanism to iterate over all threads in the system, optionally restricted to the threads associated with a specific CPU, invoking a caller-supplied function for each thread.
<<<
RELATIONS:
- TYPE: Parent
  VALUE: ZEP-SYRS-15
- TYPE: Parent
  VALUE: ZEP-SYRS-16

[REQUIREMENT]
UID: ZEP-SRS-1-27
STATUS: Draft
TYPE: Functional
COMPONENT: Threads
TITLE: Querying thread stack usage
STATEMENT: >>>
Where thread stack information is enabled, the Zephyr RTOS shall provide a mechanism to determine the amount of stack space a thread has used.
<<<
RELATIONS:
- TYPE: Parent
  VALUE: ZEP-SYRS-15
- TYPE: Parent
  VALUE: ZEP-SYRS-16

[REQUIREMENT]
UID: ZEP-SRS-1-28
STATUS: Draft
TYPE: Functional
COMPONENT: Threads
TITLE: Thread runtime statistics
STATEMENT: >>>
Where thread runtime statistics are enabled, the Zephyr RTOS shall provide a mechanism to query per-thread runtime usage statistics.
<<<
RELATIONS:
- TYPE: Parent
  VALUE: ZEP-SYRS-15
- TYPE: Parent
  VALUE: ZEP-SYRS-16

[REQUIREMENT]
UID: ZEP-SRS-1-29
STATUS: Draft
TYPE: Functional
COMPONENT: Threads
TITLE: Total system runtime statistics
STATEMENT: >>>
Where thread runtime statistics are enabled, the Zephyr RTOS shall provide a mechanism to query the total runtime usage statistics across all threads.
<<<
RELATIONS:
- TYPE: Parent
  VALUE: ZEP-SYRS-15
- TYPE: Parent
  VALUE: ZEP-SYRS-16

[REQUIREMENT]
UID: ZEP-SRS-1-30
STATUS: Draft
TYPE: Functional
COMPONENT: Threads
TITLE: Runtime stack safety monitoring
STATEMENT: >>>
Where thread runtime stack safety is enabled, the Zephyr RTOS shall provide a mechanism to check at run time whether a thread's unused stack space has fallen below a configured threshold.
<<<
RELATIONS:
- TYPE: Parent
  VALUE: ZEP-SYRS-15
- TYPE: Parent
  VALUE: ZEP-SYRS-16

[REQUIREMENT]
UID: ZEP-SRS-1-31
STATUS: Draft
TYPE: Functional
COMPONENT: Threads
TITLE: Main thread
STATEMENT: >>>
Where multithreading is enabled, the Zephyr RTOS shall provide a main thread that executes the application entry point after system initialization.
<<<
RELATIONS:
- TYPE: Parent
  VALUE: ZEP-SYRS-15
- TYPE: Parent
  VALUE: ZEP-SYRS-16

[REQUIREMENT]
UID: ZEP-SRS-1-32
STATUS: Draft
TYPE: Functional
COMPONENT: Threads
TITLE: Idle thread
STATEMENT: >>>
The Zephyr RTOS shall provide an idle thread that executes when no other thread is ready to run.
<<<
RELATIONS:
- TYPE: Parent
  VALUE: ZEP-SYRS-15
- TYPE: Parent
  VALUE: ZEP-SYRS-16

[REQUIREMENT]
UID: ZEP-SRS-1-33
STATUS: Draft
TYPE: Functional
COMPONENT: Threads
TITLE: Querying a thread's pending timeout
STATEMENT: >>>
The Zephyr RTOS shall provide an interface to query the time remaining until, and the absolute system tick of, a thread's pending timeout.
<<<
RELATIONS:
- TYPE: Parent
  VALUE: ZEP-SYRS-15
- TYPE: Parent
  VALUE: ZEP-SYRS-16

[REQUIREMENT]
UID: ZEP-SRS-1-34
STATUS: Draft
TYPE: Functional
COMPONENT: Threads
TITLE: Enabling and disabling thread runtime statistics
STATEMENT: >>>
Where thread runtime statistics are enabled, the Zephyr RTOS shall provide a mechanism to enable and disable runtime statistics collection for an individual thread and for the system as a whole.
<<<
RELATIONS:
- TYPE: Parent
  VALUE: ZEP-SYRS-15
- TYPE: Parent
  VALUE: ZEP-SYRS-16
