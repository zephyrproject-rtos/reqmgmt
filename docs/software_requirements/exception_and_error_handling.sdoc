[DOCUMENT]
TITLE: Exception and Error Handling
REQ_PREFIX: ZEP-SRS-16-

[GRAMMAR]
IMPORT_FROM_FILE: software_requirements.sgra

[TEXT]
STATEMENT: >>>
SPDX-License-Identifier: Apache-2.0
<<<

[REQUIREMENT]
UID: ZEP-SRS-16-1
STATUS: Draft
TYPE: Functional
COMPONENT: Exception and Error Handling
TITLE: Default exception handlers
STATEMENT: >>>
The Zephyr RTOS shall provide a default handler for each CPU exception defined by
the underlying architecture.
<<<
RELATIONS:
- TYPE: Parent
  VALUE: ZEP-SYRS-5

[REQUIREMENT]
UID: ZEP-SRS-16-2
STATUS: Draft
TYPE: Functional
COMPONENT: Exception and Error Handling
TITLE: Default fatal error handler
STATEMENT: >>>
The Zephyr RTOS shall provide a default fatal error handler.
<<<
RELATIONS:
- TYPE: Parent
  VALUE: ZEP-SYRS-5

[REQUIREMENT]
UID: ZEP-SRS-16-3
STATUS: Draft
TYPE: Functional
COMPONENT: Exception and Error Handling
TITLE: Exceptions treated as fatal errors by default
STATEMENT: >>>
When an exception is handled by the default exception handler, the Zephyr RTOS shall
treat the exception as a fatal error.
<<<
RELATIONS:
- TYPE: Parent
  VALUE: ZEP-SYRS-5

[REQUIREMENT]
UID: ZEP-SRS-16-4
STATUS: Draft
TYPE: Functional
COMPONENT: Exception and Error Handling
TITLE: Application-defined fatal error handler
STATEMENT: >>>
The Zephyr RTOS shall allow an application to provide, at build time, its own fatal
error handler in place of the default handler.
<<<
RELATIONS:
- TYPE: Parent
  VALUE: ZEP-SYRS-5

[REQUIREMENT]
UID: ZEP-SRS-16-5
STATUS: Draft
TYPE: Functional
COMPONENT: Exception and Error Handling
TITLE: Triggering a fatal error in the current context
STATEMENT: >>>
The Zephyr RTOS shall provide a mechanism for software to raise a fatal error attributed
to the current execution context.
<<<
RELATIONS:
- TYPE: Parent
  VALUE: ZEP-SYRS-5

[REQUIREMENT]
UID: ZEP-SRS-16-6
STATUS: Draft
TYPE: Functional
COMPONENT: Exception and Error Handling
TITLE: Triggering a fatal system error
STATEMENT: >>>
The Zephyr RTOS shall provide a mechanism for software to raise a fatal error that is
treated as unrecoverable.
<<<
RELATIONS:
- TYPE: Parent
  VALUE: ZEP-SYRS-5

[REQUIREMENT]
UID: ZEP-SRS-16-7
STATUS: Draft
TYPE: Functional
COMPONENT: Exception and Error Handling
TITLE: Fatal error reason
STATEMENT: >>>
When a fatal error handler is invoked, the Zephyr RTOS shall provide a reason code identifying the type of error.
<<<
RELATIONS:
- TYPE: Parent
  VALUE: ZEP-SYRS-5

[REQUIREMENT]
UID: ZEP-SRS-16-8
STATUS: Draft
TYPE: Functional
COMPONENT: Exception and Error Handling
TITLE: Default fatal error policy
STATEMENT: >>>
When a fatal error is handled by the default fatal error handler, the Zephyr RTOS
shall halt the system.
<<<
RELATIONS:
- TYPE: Parent
  VALUE: ZEP-SYRS-5

[REQUIREMENT]
UID: ZEP-SRS-16-9
STATUS: Draft
TYPE: Functional
COMPONENT: Exception and Error Handling
TITLE: System reset on fatal error
STATEMENT: >>>
Where reset on fatal error is enabled, when a fatal error is handled by the default
fatal error handler, the Zephyr RTOS shall reset the system instead of halting it.
<<<
RELATIONS:
- TYPE: Parent
  VALUE: ZEP-SYRS-5

[REQUIREMENT]
UID: ZEP-SRS-16-10
STATUS: Draft
TYPE: Functional
COMPONENT: Exception and Error Handling
TITLE: Recovery from a fatal error in thread context
STATEMENT: >>>
When the application-provided fatal error handler returns following a recoverable
fatal error attributed to a thread, the Zephyr RTOS shall terminate the offending
thread and continue operation.
<<<
RELATIONS:
- TYPE: Parent
  VALUE: ZEP-SYRS-5

[REQUIREMENT]
UID: ZEP-SRS-16-11
STATUS: Draft
TYPE: Functional
COMPONENT: Exception and Error Handling
TITLE: No recovery from an unrecoverable fatal error
STATEMENT: >>>
Where kernel assertions are enabled, when the application-provided fatal error
handler returns following an unrecoverable fatal error, the Zephyr RTOS shall halt
the system.
<<<
RELATIONS:
- TYPE: Parent
  VALUE: ZEP-SYRS-5

[REQUIREMENT]
UID: ZEP-SRS-16-12
STATUS: Draft
TYPE: Functional
COMPONENT: Exception and Error Handling
TITLE: Fatal errors in interrupt context are unrecoverable
STATEMENT: >>>
If a fatal error other than a thread stack overflow occurs in interrupt context,
then the Zephyr RTOS shall treat the error as unrecoverable.
<<<
RELATIONS:
- TYPE: Parent
  VALUE: ZEP-SYRS-5

[REQUIREMENT]
UID: ZEP-SRS-16-13
STATUS: Draft
TYPE: Functional
COMPONENT: Exception and Error Handling
TITLE: Fatal error diagnostics
STATEMENT: >>>
Where exception dump output is enabled, when a fatal error occurs, the Zephyr RTOS
shall report diagnostic information identifying the reason for the error and the
execution context in which it occurred.
<<<
RELATIONS:
- TYPE: Parent
  VALUE: ZEP-SYRS-5
