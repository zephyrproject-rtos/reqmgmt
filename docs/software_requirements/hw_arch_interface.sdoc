[DOCUMENT]
TITLE: Hardware Architecture Interface
REQ_PREFIX: ZEP-SRS-19-

[GRAMMAR]
IMPORT_FROM_FILE: software_requirements.sgra

[TEXT]
STATEMENT: >>>
SPDX-License-Identifier: Apache-2.0
<<<

[REQUIREMENT]
UID: ZEP-SRS-19-1
STATUS: Draft
TYPE: Functional
COMPONENT: Hardware Architecture Interface
TITLE: Atomic Operations
STATEMENT: >>>
The Zephyr RTOS shall provide an interface to access memory while ensuring mutual exclusion.
<<<
USER_STORY: >>>
As a Zephyr RTOS user I want to read from or write into a memory areas without being disturbed by other threads or ISRs.
<<<
RELATIONS:
- TYPE: Parent
  VALUE: ZEP-SYRS-1

[REQUIREMENT]
UID: ZEP-SRS-19-2
STATUS: Draft
TYPE: Functional
COMPONENT: Hardware Architecture Interface
TITLE: Thread Context Switching
STATEMENT: >>>
The Zephyr RTOS shall provide a mechanism for context switching between threads.
<<<
USER_STORY: >>>
As a Zephyr RTOS user I want to execute code concurrently in one or more threads and when interrupted at a code location in a thread, to continue at the very same location.
<<<
RELATIONS:
- TYPE: Parent
  VALUE: ZEP-SYRS-1

[REQUIREMENT]
UID: ZEP-SRS-19-3
STATUS: Draft
TYPE: Functional
COMPONENT: Hardware Architecture Interface
TITLE: Software Exceptions
STATEMENT: >>>
The Zephyr RTOS shall provide an interface to implement software exceptions.
<<<
USER_STORY: >>>
As a Zephyr RTOS user I want to catch any software exception and handle it according to my application needs.
<<<
RELATIONS:
- TYPE: Parent
  VALUE: ZEP-SYRS-1

[REQUIREMENT]
UID: ZEP-SRS-19-28
STATUS: Draft
TYPE: Functional
COMPONENT: Hardware Architecture Interface
TITLE: 32-bit and 64-bit architectures
STATEMENT: >>>
The Zephyr RTOS shall support processor architectures with 32-bit and with 64-bit
native word sizes.
<<<
RELATIONS:
- TYPE: Parent
  VALUE: ZEP-SYRS-1

[[SECTION]]
TITLE: User Mode Support

[REQUIREMENT]
UID: ZEP-SRS-19-4
STATUS: Draft
TYPE: Functional
COMPONENT: Hardware Architecture Interface
TITLE: Entering user mode
STATEMENT: >>>
Where user mode is supported, the Zephyr RTOS shall provide an interface to transition the executing thread from supervisor mode to user mode.
<<<
USER_STORY: >>>
As a Zephyr RTOS user I want the kernel to execute code at the appropriate processor privilege level (for example supervisor and user mode) so that privileged and unprivileged execution are kept separate.
<<<
RELATIONS:
- TYPE: Parent
  VALUE: ZEP-SYRS-1

[REQUIREMENT]
UID: ZEP-SRS-19-13
STATUS: Draft
TYPE: Functional
COMPONENT: Hardware Architecture Interface
TITLE: Execution mode query
STATEMENT: >>>
Where user mode is supported, the Zephyr RTOS shall provide an interface to query whether the current execution context is running in user mode.
<<<
RELATIONS:
- TYPE: Parent
  VALUE: ZEP-SYRS-1

[REQUIREMENT]
UID: ZEP-SRS-19-14
STATUS: Draft
TYPE: Functional
COMPONENT: Hardware Architecture Interface
TITLE: System call invocation
STATEMENT: >>>
Where user mode is supported, the Zephyr RTOS shall provide an interface for user mode code to invoke system calls that execute in supervisor mode.
<<<
RELATIONS:
- TYPE: Parent
  VALUE: ZEP-SYRS-1

[[/SECTION]]

[[SECTION]]
TITLE: Cache Management

[REQUIREMENT]
UID: ZEP-SRS-19-5
STATUS: Draft
TYPE: Functional
COMPONENT: Hardware Architecture Interface
TITLE: Data cache flush
STATEMENT: >>>
Where a data cache is present, the Zephyr RTOS shall provide an interface to flush the data cache, over the entire cache or a specified address range.
<<<
RELATIONS:
- TYPE: Parent
  VALUE: ZEP-SYRS-1

[REQUIREMENT]
UID: ZEP-SRS-19-15
STATUS: Draft
TYPE: Functional
COMPONENT: Hardware Architecture Interface
TITLE: Data cache invalidation
STATEMENT: >>>
Where a data cache is present, the Zephyr RTOS shall provide an interface to invalidate the data cache, over the entire cache or a specified address range.
<<<
RELATIONS:
- TYPE: Parent
  VALUE: ZEP-SYRS-1

[REQUIREMENT]
UID: ZEP-SRS-19-16
STATUS: Draft
TYPE: Functional
COMPONENT: Hardware Architecture Interface
TITLE: Combined data cache flush and invalidation
STATEMENT: >>>
Where a data cache is present, the Zephyr RTOS shall provide an interface to flush and invalidate the data cache in a single operation, over the entire cache or a specified address range.
<<<
RELATIONS:
- TYPE: Parent
  VALUE: ZEP-SYRS-1

[REQUIREMENT]
UID: ZEP-SRS-19-6
STATUS: Draft
TYPE: Functional
COMPONENT: Hardware Architecture Interface
TITLE: Instruction cache flush
STATEMENT: >>>
Where an instruction cache is present, the Zephyr RTOS shall provide an interface to flush the instruction cache, over the entire cache or a specified address range.
<<<
RELATIONS:
- TYPE: Parent
  VALUE: ZEP-SYRS-1

[REQUIREMENT]
UID: ZEP-SRS-19-17
STATUS: Draft
TYPE: Functional
COMPONENT: Hardware Architecture Interface
TITLE: Instruction cache invalidation
STATEMENT: >>>
Where an instruction cache is present, the Zephyr RTOS shall provide an interface to invalidate the instruction cache, over the entire cache or a specified address range.
<<<
RELATIONS:
- TYPE: Parent
  VALUE: ZEP-SYRS-1

[REQUIREMENT]
UID: ZEP-SRS-19-18
STATUS: Draft
TYPE: Functional
COMPONENT: Hardware Architecture Interface
TITLE: Combined instruction cache flush and invalidation
STATEMENT: >>>
Where an instruction cache is present, the Zephyr RTOS shall provide an interface to flush and invalidate the instruction cache in a single operation, over the entire cache or a specified address range.
<<<
RELATIONS:
- TYPE: Parent
  VALUE: ZEP-SYRS-1

[REQUIREMENT]
UID: ZEP-SRS-19-7
STATUS: Draft
TYPE: Functional
COMPONENT: Hardware Architecture Interface
TITLE: Enabling the data cache
STATEMENT: >>>
Where a data cache is present, the Zephyr RTOS shall provide an interface to enable
the data cache.
<<<
RELATIONS:
- TYPE: Parent
  VALUE: ZEP-SYRS-1

[REQUIREMENT]
UID: ZEP-SRS-19-21
STATUS: Draft
TYPE: Functional
COMPONENT: Hardware Architecture Interface
TITLE: Disabling the data cache
STATEMENT: >>>
Where a data cache is present, the Zephyr RTOS shall provide an interface to disable
the data cache.
<<<
RELATIONS:
- TYPE: Parent
  VALUE: ZEP-SYRS-1

[REQUIREMENT]
UID: ZEP-SRS-19-19
STATUS: Draft
TYPE: Functional
COMPONENT: Hardware Architecture Interface
TITLE: Enabling the instruction cache
STATEMENT: >>>
Where an instruction cache is present, the Zephyr RTOS shall provide an interface to
enable the instruction cache.
<<<
RELATIONS:
- TYPE: Parent
  VALUE: ZEP-SYRS-1

[REQUIREMENT]
UID: ZEP-SRS-19-22
STATUS: Draft
TYPE: Functional
COMPONENT: Hardware Architecture Interface
TITLE: Disabling the instruction cache
STATEMENT: >>>
Where an instruction cache is present, the Zephyr RTOS shall provide an interface to
disable the instruction cache.
<<<
RELATIONS:
- TYPE: Parent
  VALUE: ZEP-SYRS-1

[REQUIREMENT]
UID: ZEP-SRS-19-8
STATUS: Draft
TYPE: Functional
COMPONENT: Hardware Architecture Interface
TITLE: Data cache line size query
STATEMENT: >>>
Where a data cache is present, the Zephyr RTOS shall provide an interface to obtain the data cache line size.
<<<
RELATIONS:
- TYPE: Parent
  VALUE: ZEP-SYRS-1

[REQUIREMENT]
UID: ZEP-SRS-19-20
STATUS: Draft
TYPE: Functional
COMPONENT: Hardware Architecture Interface
TITLE: Instruction cache line size query
STATEMENT: >>>
Where an instruction cache is present, the Zephyr RTOS shall provide an interface to obtain the instruction cache line size.
<<<
RELATIONS:
- TYPE: Parent
  VALUE: ZEP-SYRS-1

[REQUIREMENT]
UID: ZEP-SRS-19-9
STATUS: Draft
TYPE: Functional
COMPONENT: Hardware Architecture Interface
TITLE: Memory coherence reporting
STATEMENT: >>>
Where the architecture can determine memory coherence, the Zephyr RTOS shall provide
an interface to report whether the memory at a given address is coherent with respect
to the data cache.
<<<
RELATIONS:
- TYPE: Parent
  VALUE: ZEP-SYRS-1

[[/SECTION]]

[[SECTION]]
TITLE: Memory Barriers

[REQUIREMENT]
UID: ZEP-SRS-19-25
STATUS: Draft
TYPE: Functional
COMPONENT: Hardware Architecture Interface
TITLE: Full data memory barrier
STATEMENT: >>>
The Zephyr RTOS shall provide a mechanism to enforce sequentially consistent
ordering of memory accesses around a point in the program (a full data memory
barrier).
<<<
RELATIONS:
- TYPE: Parent
  VALUE: ZEP-SYRS-1

[REQUIREMENT]
UID: ZEP-SRS-19-26
STATUS: Draft
TYPE: Functional
COMPONENT: Hardware Architecture Interface
TITLE: Data synchronization barrier
STATEMENT: >>>
The Zephyr RTOS shall provide a mechanism to ensure that all outstanding memory
accesses complete before subsequent instructions execute (a data synchronization
barrier).
<<<
RELATIONS:
- TYPE: Parent
  VALUE: ZEP-SYRS-1

[REQUIREMENT]
UID: ZEP-SRS-19-27
STATUS: Draft
TYPE: Functional
COMPONENT: Hardware Architecture Interface
TITLE: Cross-core synchronization barrier
STATEMENT: >>>
The Zephyr RTOS shall provide a mechanism to synchronize memory accesses across
all cores (a system-wide synchronization barrier).
<<<
RELATIONS:
- TYPE: Parent
  VALUE: ZEP-SYRS-1

[[/SECTION]]

[[SECTION]]
TITLE: Diagnostics and Debug

[REQUIREMENT]
UID: ZEP-SRS-19-10
STATUS: Draft
TYPE: Functional
COMPONENT: Hardware Architecture Interface
TITLE: Call stack unwinding
STATEMENT: >>>
Where stack unwinding is supported, the Zephyr RTOS shall provide an interface to walk the call stack of a thread and report each stack frame to a caller-supplied function.
<<<
RELATIONS:
- TYPE: Parent
  VALUE: ZEP-SYRS-1

[REQUIREMENT]
UID: ZEP-SRS-19-11
STATUS: Draft
TYPE: Functional
COMPONENT: Hardware Architecture Interface
TITLE: Core dump processor state capture
STATEMENT: >>>
Where core dump support is enabled, the Zephyr RTOS shall provide an interface to capture architecture-specific processor state for inclusion in a core dump.
<<<
RELATIONS:
- TYPE: Parent
  VALUE: ZEP-SYRS-1

[REQUIREMENT]
UID: ZEP-SRS-19-12
STATUS: Draft
TYPE: Functional
COMPONENT: Hardware Architecture Interface
TITLE: Debugger access to processor registers
STATEMENT: >>>
Where a debug stub is enabled, the Zephyr RTOS shall provide an interface for an
external debugger to read and write the processor registers.
<<<
RELATIONS:
- TYPE: Parent
  VALUE: ZEP-SYRS-1

[REQUIREMENT]
UID: ZEP-SRS-19-23
STATUS: Draft
TYPE: Functional
COMPONENT: Hardware Architecture Interface
TITLE: Debugger breakpoint control
STATEMENT: >>>
Where a debug stub is enabled, the Zephyr RTOS shall provide an interface for an
external debugger to set and remove breakpoints.
<<<
RELATIONS:
- TYPE: Parent
  VALUE: ZEP-SYRS-1

[REQUIREMENT]
UID: ZEP-SRS-19-24
STATUS: Draft
TYPE: Functional
COMPONENT: Hardware Architecture Interface
TITLE: Debugger single-step execution
STATEMENT: >>>
Where a debug stub is enabled, the Zephyr RTOS shall provide an interface for an
external debugger to single-step execution.
<<<
RELATIONS:
- TYPE: Parent
  VALUE: ZEP-SYRS-1

[[/SECTION]]
