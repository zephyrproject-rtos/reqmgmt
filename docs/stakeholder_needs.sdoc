[DOCUMENT]
TITLE: Zephyr Stakeholder Needs
REQ_PREFIX: ZEP-

[GRAMMAR]
ELEMENTS:
- TAG: STAKEHOLDER_NEED
  FIELDS:
  - TITLE: UID
    TYPE: String
    REQUIRED: False
  - TITLE: STATUS
    TYPE: String
    REQUIRED: False
  - TITLE: TYPE
    TYPE: String
    REQUIRED: False
  - TITLE: TITLE
    TYPE: String
    REQUIRED: False
  - TITLE: STATEMENT
    TYPE: String
    REQUIRED: False
  RELATIONS:
  - TYPE: Parent
  - TYPE: File

[FREETEXT]
TBD
[/FREETEXT]

[STAKEHOLDER_NEED]
UID: ZEP-127
STATUS: Draft
TYPE: Need
TITLE: Architecture Layer Interface
STATEMENT: >>>
As a Zephyr RTOS user I want to be able to easily switch my application to a different MCU architecture (x86, ARM Cortex-M/A, RISCV etc.).
<<<

[STAKEHOLDER_NEED]
UID: ZEP-128
STATUS: Draft
TYPE: Need
TITLE: Support multiprocessor management
STATEMENT: >>>
As a Zephyr RTOS user I want to use Zephyr OS on multi core (SMP-)MCUs/MPUs.
<<<

[STAKEHOLDER_NEED]
UID: ZEP-129
STATUS: Draft
TYPE: Need
TITLE: Support Subset of Standard C Library
STATEMENT: >>>
As a Zephyr RTOS user I want to have a selection of standard C library implementations e.g. a full extend and a minimal with a smaller footprint or a particular fast executing implementation.
<<<

[STAKEHOLDER_NEED]
UID: ZEP-130
STATUS: Draft
TYPE: Need
TITLE: Device Driver Abstraction
STATEMENT: >>>
As a Zephyr RTOS user I want my application to be portable between different MCU architectures (ARM Cortex-M/A, Intel x86, RISCV etc.) and MCU vendors (STM, NXP, Intel, etc.) without having to change the MCU peripherals access.
<<<

[STAKEHOLDER_NEED]
UID: ZEP-131
STATUS: Draft
TYPE: Need
TITLE: Fatal error and exception handling
STATEMENT: >>>
As a Zephyr RTOS user I want errors and exceptions to handled and react according to my applications requirements (e.g. reach/establish the applications safety state).
<<<

[STAKEHOLDER_NEED]
UID: ZEP-132
STATUS: Draft
TYPE: Need
TITLE: Common File system operation support
STATEMENT: >>>
As a Zephyr RTOS user I want a posix / c like file system access to store data.
<<<

[STAKEHOLDER_NEED]
UID: ZEP-133
STATUS: Draft
TYPE: Need
TITLE: Interrupt Service Routine
STATEMENT: >>>
As a Zephyr RTOS user I want interrupts to be handled synchronously in response to a hardware or software interrupt request with a minimum latency, preempting threads and, as far as the hardware allows, lower priority interrupt service routines.
<<<

[STAKEHOLDER_NEED]
UID: ZEP-134
STATUS: Draft
TYPE: Need
TITLE: Logging
STATEMENT: >>>
As a Zephyr RTOS user I want to be able to log application defined events as well as framework exceptions.
<<<

[STAKEHOLDER_NEED]
UID: ZEP-135
STATUS: Draft
TYPE: Need
TITLE: Memory Management framework
STATEMENT: >>>
As a Zephyr RTOS user I want memory to be allocated and protected to my application threads preventing mistakenly access to foreign memory as far as the hardware allows.
<<<

[STAKEHOLDER_NEED]
UID: ZEP-136
STATUS: Draft
TYPE: Need
TITLE: Power Management
STATEMENT: >>>
As a Zephyr RTOS user I want to be able to control the power mode of the MCU and its peripherals to take advantage of the hardware features and to be able to implement low power or battery driven long life applications.
<<<

[STAKEHOLDER_NEED]
UID: ZEP-137
STATUS: Draft
TYPE: Need
TITLE: Multiple CPU scheduling
STATEMENT: >>>
As a Zephyr RTOS user I want Zephyr OS to run on MCUs/CPUs with one or more CPU cores.
<<<

[STAKEHOLDER_NEED]
UID: ZEP-138
STATUS: Draft
TYPE: Need
TITLE: Scheduling
STATEMENT: >>>
As a Zephyr RTOS user, I want to be able to control which thread will run on which CPU.
<<<

[STAKEHOLDER_NEED]
UID: ZEP-139
STATUS: Draft
TYPE: Need
TITLE: Mutex
STATEMENT: >>>
As a Zephyr RTOS user I want to able to exchange information between threads in a thread-safe manner guaranteeing data consistence.
<<<

[STAKEHOLDER_NEED]
UID: ZEP-140
STATUS: Draft
TYPE: Need
TITLE: Counting Semaphore
STATEMENT: >>>
As a software developer threaded with implementing resource management in our real-time operating system (RTOS), I want to integrate a semaphore synchronization primitive to facilitate coordinated access to shared resources among multiple threads.
<<<

[STAKEHOLDER_NEED]
UID: ZEP-141
STATUS: Draft
TYPE: Need
TITLE: Thread support
STATEMENT: >>>
As a Zephyr RTOS user, I want to be able to have support for the kernel objects named threads for processing work.
<<<

[STAKEHOLDER_NEED]
UID: ZEP-142
STATUS: Draft
TYPE: Need
TITLE: Thread management
STATEMENT: >>>
As a Zephyr RTOS user, I want to be able to manage the execute of multiple threads with different priorities.
<<<

[STAKEHOLDER_NEED]
UID: ZEP-143
STATUS: Draft
TYPE: Need
TITLE: Thread priority
STATEMENT: >>>
As a Zephyr RTOS user, I want to be able to give my threads different priorities for execution.
<<<
