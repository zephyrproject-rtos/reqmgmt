[DOCUMENT]
TITLE: Zephyr Requirements
OPTIONS:
  MARKUP: Text

[GRAMMAR]
ELEMENTS:
- TAG: REQUIREMENT
  FIELDS:
  - TITLE: UID
    TYPE: String
    REQUIRED: False
  - TITLE: TYPE
    TYPE: String
    REQUIRED: False
  - TITLE: COMPONENT
    TYPE: String
    REQUIRED: False
  - TITLE: REFS
    TYPE: Reference(ParentReqReference)
    REQUIRED: False
  - TITLE: TITLE
    TYPE: String
    REQUIRED: False
  - TITLE: STATEMENT
    TYPE: String
    REQUIRED: False
  - TITLE: USER_STORY
    TYPE: String
    REQUIRED: False
  - TITLE: DISCUSSION_DATE
    TYPE: String
    REQUIRED: False
  - TITLE: REVIEW_COMMENT
    TYPE: String
    REQUIRED: False

[REQUIREMENT]
UID: ZEP-ARCH-001
TYPE: High Level
COMPONENT: Hardware Architecture Interface (KS: Should this be Abstraction rather than Architecture?)
TITLE: Architecture Layer Interface
STATEMENT: >>>
Zephyr shall provide a framework for applications running on Zephyr to communicate with the hardware architectural service available from Zephyr for the system
<<<
USER_STORY: >>>
As a Zephyr OS user I want to be able to easily switch my application to a different MCU architecture (x86, ARM Cortex-M/A, RISCV etc.)
<<<
DISCUSSION_DATE: >>>
2022/3/30 - ok - pf
<<<

[REQUIREMENT]
UID: ZEP-ARCH-002
TYPE: Functional
COMPONENT: Hardware Architecture Interface
REFS:
- TYPE: Parent
  VALUE: ZEP-ARCH-001
TITLE: Atomic Operations
STATEMENT: >>>
Zephyr shall provide an interface functionality to access memory while ensuring mutual exclusion. Note: Implementation by atomic variables and accessing them by APIs
<<<
USER_STORY: >>>
As a Zephyr OS user I want to read from or write into a memory areas without being disturbed by other threads or ISRs
<<<
DISCUSSION_DATE: >>>
2022/3/30 - ok - pq
<<<

[REQUIREMENT]
UID: ZEP-ARCH-003
TYPE: Functional
COMPONENT: Hardware Architecture Interface
REFS:
- TYPE: Parent
  VALUE: ZEP-ARCH-001
TITLE: Context switch between threads
STATEMENT: >>>
Zephyr shall provide a mechanism for context switching between threads.
<<<
USER_STORY: >>>
As a Zephyr OS user I want to execute code concurrently in one or more threads and when interrupted at a code location in a thread, to continue at the very same location.
<<<
DISCUSSION_DATE: >>>
2022/3/30 - ok - pf
<<<

[REQUIREMENT]
UID: ZEP-ARCH-004
TYPE: Functional
COMPONENT: Hardware Architecture Interface
REFS:
- TYPE: Parent
  VALUE: ZEP-ARCH-001
TITLE: Enable hardware exceptions
STATEMENT: >>>
Zephyr shall provide an interface to allow the hardware architecture to implement software exceptions.
<<<
USER_STORY: >>>
As a Zephyr OS user I want to catch any hardware fault / exception and handle it according to my application needs.
<<<
DISCUSSION_DATE: >>>
2022/3/30 - ok - pq
<<<

[REQUIREMENT]
UID: ZEPH-ARCH-005
TYPE: Functional
COMPONENT: Hardware Architecture Interface
REFS:
- TYPE: Parent
  VALUE: ZEP-ARCH-001
TITLE: Manage lifecycle of running processor
STATEMENT: >>>
Zephyr shall provide utilities an interface for managing  processor  modes
<<<
USER_STORY: >>>
If MCU power state was meant here:
As a Zephyr OS user I want to control the MCU's power saving mode such e.g. operation, sleep, deep sleep or similar as supported by the selected MCU
<<<
DISCUSSION_DATE: >>>
2022/7/21 - ok - pf
<<<
REVIEW_COMMENT: >>>
What is lifecycle - power on, standby, power off?  or ???? 

Clarification: Starting and Stopping, and putting it into Stand-By Mode (whatever the processor supports)
<<<

[REQUIREMENT]
UID: ZEP-ARCH-006
TYPE: High Level
COMPONENT: Hardware Architecture Interface
REFS:
- TYPE: Parent
  VALUE: ZEP-ARCH-001
TITLE: Support multiprocessor management
STATEMENT: >>>
Zephyr shall support multiprocessing management facilities.
<<<
USER_STORY: >>>
As a Zephyr OS user I want to use Zephyr OS on multi core (SMP-)MCUs/MPUs
<<<
DISCUSSION_DATE: >>>
Still need to articulate the capabilities explicitly.
<<<
REVIEW_COMMENT: >>>
From the Docs: No special application code needs to be written to take advantage of this feature
<<<

[REQUIREMENT]
UID: ZEP-CLIB-001
TYPE: High Level
COMPONENT: C Library
TITLE: C Library Support
STATEMENT: >>>
Zephyr shall support a hooks to interface to a subset of the standard C library.
<<<
USER_STORY: >>>
As a Zephyr OS user I want to have a selection of standard C library implementations e.g. a full extend and a minimal with a smaller footprint or a particular fast executing implementation.
<<<
DISCUSSION_DATE: >>>
We needed to do a subset description, and need to be specific about the subset.
<<<
REVIEW_COMMENT: >>>
Can we limit the type of C library implementations? Testing might be hell if we do not limit ourselfes to the ones defined? Like "miminal libc" and "newlib". Will it make sense to pull miminal Libc into the certification scope?

Clarification: Would prefer to cover the scope part first. Talking about the hooks which apply to each C Library. Open, Close, Diff. Hooks that are OS dependent. C or Library dependent. ref https://github.com/zephyrproject-rtos/zephyr/blob/main/lib/libc/newlib/libc-hooks.c
<<<

[REQUIREMENT]
UID: ZEP-CLIB-002
TYPE: Functional
COMPONENT: C Library
REFS:
- TYPE: Parent
  VALUE: ZEP-CLIB-001
STATEMENT: >>>
Zephyr shall support formatted output
<<<
USER_STORY: >>>
(targets for *printf having variable argument list)
<<<
DISCUSSION_DATE: >>>
20221122.0
<<<

[REQUIREMENT]
UID: ZEP-CLIB-003
TYPE: Functional
COMPONENT: C Library
REFS:
- TYPE: Parent
  VALUE: ZEP-CLIB-001
STATEMENT: >>>
Zephyr shall support floating point math libraries for processors where floating point is available.
<<<
USER_STORY: >>>
https://github.com/zephyrproject-rtos/zephyr/blob/main/lib/libc/minimal/include/math.h
<<<
DISCUSSION_DATE: >>>
20221122.0
<<<

[REQUIREMENT]
UID: ZEP-CLIB-004
TYPE: Functional
COMPONENT: C Library
REFS:
- TYPE: Parent
  VALUE: ZEP-CLIB-001
STATEMENT: >>>
Zephyr shall support boolean primitives
<<<
USER_STORY: >>>
https://github.com/zephyrproject-rtos/zephyr/blob/main/lib/libc/minimal/include/stdbool.h
<<<
DISCUSSION_DATE: >>>
20221122.0
<<<

[REQUIREMENT]
UID: ZEP-CLIB-005
TYPE: Functional
COMPONENT: C Library
REFS:
- TYPE: Parent
  VALUE: ZEP-CLIB-001
STATEMENT: >>>
Zephyr shall support the standard unix time interface
<<<
USER_STORY: >>>
https://github.com/zephyrproject-rtos/zephyr/blob/main/lib/libc/minimal/include/time.h
<<<
DISCUSSION_DATE: >>>
20221122.0
<<<

[REQUIREMENT]
UID: ZEP-CLIB-006
TYPE: Functional
COMPONENT: C Library
REFS:
- TYPE: Parent
  VALUE: ZEP-CLIB-001
STATEMENT: >>>
Zephyr shall support an interface to manage strings
<<<
USER_STORY: >>>
https://github.com/zephyrproject-rtos/zephyr/blob/main/lib/libc/minimal/include/strings.h
<<<
DISCUSSION_DATE: >>>
20221122.0
<<<

[REQUIREMENT]
UID: ZEP-CLIB-007
TYPE: Functional
COMPONENT: C Library
REFS:
- TYPE: Parent
  VALUE: ZEP-CLIB-001
STATEMENT: >>>
Zephyr shall support an interface to move contents between regions of memory
<<<
USER_STORY: >>>
https://github.com/zephyrproject-rtos/zephyr/blob/main/lib/libc/minimal/include/string.h
<<<
DISCUSSION_DATE: >>>
20221122.0
<<<

[REQUIREMENT]
UID: ZEP-CLIB-008
TYPE: Functional
COMPONENT: C Library
REFS:
- TYPE: Parent
  VALUE: ZEP-CLIB-001
STATEMENT: >>>
Zephyr shall support a file i/O based interface for driver communication.
<<<
USER_STORY: >>>
https://github.com/zephyrproject-rtos/zephyr/blob/main/lib/libc/minimal/include/stdint.h
<<<
DISCUSSION_DATE: >>>
20221122.0
<<<

[REQUIREMENT]
UID: ZEP-CLIB-009
TYPE: Functional
COMPONENT: C Library
REFS:
- TYPE: Parent
  VALUE: ZEP-CLIB-001
STATEMENT: >>>
Zephyr shall support standard C99 integer types
<<<
USER_STORY: >>>
https://github.com/zephyrproject-rtos/zephyr/blob/main/lib/libc/minimal/include/stdint.h https://github.com/zephyrproject-rtos/zephyr/blob/main/lib/libc/minimal/include/limits.h
<<<
DISCUSSION_DATE: >>>
20221122.0
<<<

[REQUIREMENT]
UID: ZEP-CLIB-010
TYPE: Functional
COMPONENT: C Library
REFS:
- TYPE: Parent
  VALUE: ZEP-CLIB-001
STATEMENT: >>>
Zephyr shall support standard system error numbers as defined by IEEE Std 1003.1-2017
<<<
USER_STORY: >>>
https://github.com/zephyrproject-rtos/zephyr/blob/main/lib/libc/minimal/include/errno.h
<<<
DISCUSSION_DATE: >>>
20221129.0
<<<

[REQUIREMENT]
UID: ZEP-CLIB-011
TYPE: Functional
COMPONENT: C Library
REFS:
- TYPE: Parent
  VALUE: ZEP-CLIB-001
STATEMENT: >>>
The set of C Libraries supported by Zephyr needs to be defined documented in the Zephyr Safety Manual
<<<
USER_STORY: >>>
As a Zephyr OS user implementing a safety application I want to have documented which C library functions are supported.
<<<
DISCUSSION_DATE: >>>
revisit after subset defined
<<<

[REQUIREMENT]
UID: ZEP-CLIB-012
TYPE: Functional
COMPONENT: C Library
REFS:
- TYPE: Parent
  VALUE: ZEP-CLIB-001
STATEMENT: >>>
The Zephyr Safety Manual needs to specify how to configure the support of external C Libraries
<<<
USER_STORY: >>>
As a Zephyr OS user implementing a safety application I want to have documented how I am allowed to configure (KConfig) Zephyr OS.
<<<
DISCUSSION_DATE: >>>
revisit after subset defined
<<<

[REQUIREMENT]
TYPE: High Level
COMPONENT: Utilities Library - Data Structures
TITLE: Data Structures Library Utilities
STATEMENT: >>>
Zephyr shall provide common container data structures as library utilities   (ring buffer, linked list, red black trees, ....   see document from Anas)
<<<
USER_STORY: >>>
As a Zepyhr OS developler (user) I do not want to implement common software patterns multiple time in each module again, but make use of a common library which provides it.
<<<
DISCUSSION_DATE: >>>
AI: Need to be reworked;  split into several requirements;   Library utility shall provide red-black,   shall provide ...   .   Call "Utility Libraries"
<<<
REVIEW_COMMENT: >>>
Possible API - It's ambiguous what is meant by common container data structures as library ulitileis.... - get pointer to code.   (Single linked list, double linked list, ....)

Clarification: There are many files. Linked list, ring buffer, ...). This is an implementation. Need to look at scope. Doesn't need to be a high level requirement
<<<

[REQUIREMENT]
TYPE: High Level
COMPONENT: Device Driver API
TITLE: Device Driver Abstracting
STATEMENT: >>>
Zephyr shall provide a framework for managing device driver behavior (note: device drivers includes peripherals)
<<<
USER_STORY: >>>
As a Zephyr OS user I want my application to be portable between different MCU architectures (ARM Cortex-M/A, Intel x86, RISCV etc.) and MCU vendors (STM, NXP, Intel, etc.) without having to change the MCU peripherals access.
<<<
DISCUSSION_DATE: >>>
2022/3/30 - ok - pf
<<<

[REQUIREMENT]
TYPE: Functional
COMPONENT: Device Driver API
TITLE: Device Driver Abstraction
STATEMENT: >>>
Zephyr shall provide abstraction of device drivers with common functionalities as an intermediate interface between applications and device drivers, where such interface is implemented by individual device drivers.

Proposal for replacement: Zephyr shall provide an interface between application and individual device drivers to provide an abstraction of device drivers with common functionalities.
<<<
USER_STORY: >>>
=N21 & "

Remark: What is the difference to ZEP006?"
<<<
DISCUSSION_DATE: >>>
Needs clarification - what are common functionalities?   Link to description?
<<<
REVIEW_COMMENT: >>>
What are common functionalities?

Clarification: Abstract API drivers, UART. Set of files asociated with that. Include drivers. 50+ files. Best place to look at is the documentation (not the files).
<<<

[REQUIREMENT]
TYPE: Functional
COMPONENT: Device Driver API
TITLE: Expose kernel to hardware interrupts
STATEMENT: >>>
Zephyr shall provide an interface for managing a defined set of hardware exceptions (including interupts) across all systems.
<<<
USER_STORY: >>>
As a Zephyr OS user I want hardware exeptions (hardware failures, programming mistakes) to be handled gracefully (no program crashes as far as possible).
<<<
DISCUSSION_DATE: >>>
2022/4/13 - ok - pf
<<<
REVIEW_COMMENT: >>>
What does "system" mean in this context? Architecture?

NP: Now I think system means HW platform.
<<<

[REQUIREMENT]
TYPE: High Level
COMPONENT: Exception Handling
TITLE: Fatal Exception handling
STATEMENT: >>>
The Zephyr kernel shall provide a framework for error and exception handling.
<<<
USER_STORY: >>>
As a Zephyr OS user I want errors and exeptions to handled and react according to my applications requirements (e.g. reach/establish the applications safey state).
<<<
DISCUSSION_DATE: >>>
2022/4/13 - ok -pf
<<<

[REQUIREMENT]
TYPE: Functional
COMPONENT: Fatal Exception Handling
TITLE: Fatal Exception Error Handler
STATEMENT: >>>
Zephyr shall provide default handlers for exceptions that do not have a dedicated handler
<<<
USER_STORY: >>>
As a Zephyr OS user I want execptions which I did not handle explicitely (by mistake or on purpose) to be caught by a default handler, defined either by Zephyr OS or by myself.
<<<
DISCUSSION_DATE: >>>
2022/4/13 - ok -pq - need definition of exceptions vs fatal errors
<<<

[REQUIREMENT]
TYPE: Functional
COMPONENT: Fatal Error Handling
STATEMENT: >>>
Zephyr shall provide default handlers for fatal errors that do not have a dedicated handler
<<<
USER_STORY: >>>
=N25
<<<
DISCUSSION_DATE: >>>
2022/4/13 - ok - pq
<<<

[REQUIREMENT]
TYPE: Functional
COMPONENT: Fatal Error Handling
STATEMENT: >>>
Zephyr shall provide an interface to assign a specific handler with an exception.
<<<

[REQUIREMENT]
TYPE: Functional
COMPONENT: Fatal Error Handling
STATEMENT: >>>
Zephyr shall provide an interface to assign a specific handler for a fatal error.
<<<

[REQUIREMENT]
TYPE: High Level
COMPONENT: File Systems
TITLE: Common File system operation support
STATEMENT: >>>
Zephyr shall provide a framework for managing file system access
<<<
USER_STORY: >>>
As a Zephyr OS user I want a posix / c like file system access to store data.
<<<
DISCUSSION_DATE: >>>
2022/4/13 - ok - p? - depends on set of expectations
<<<

[REQUIREMENT]
TYPE: Functional
COMPONENT: File System
STATEMENT: >>>
Zephyr shall provide write access to the files in the file system
<<<
USER_STORY: >>>
As a Zephyr OS user I want to be able to write to a file either from the beginning of the file or appending at the end.
<<<
DISCUSSION_DATE: >>>
2022/4/13 - ok - pf
<<<

[REQUIREMENT]
TYPE: Functional
COMPONENT: File System
STATEMENT: >>>
Zephyr shall provide file close capabilities for files on the file system
<<<
USER_STORY: >>>
As a Zephyr OS user I want to be able to close a file after being finished with my file operations, unlocking any access restrictions.
<<<
DISCUSSION_DATE: >>>
2022/4/13 - ok -pf
<<<

[REQUIREMENT]
TYPE: Functional
COMPONENT: File System
STATEMENT: >>>
Zephyr shall provide file open capabilities for files on the file system
<<<
USER_STORY: >>>
As a Zephyr OS user I want to be able to open a file for writing or reading.
When opened for writing, I want to have exclusive access to the file.
<<<
DISCUSSION_DATE: >>>
2022/4/13 - ok - pf
<<<

[REQUIREMENT]
TYPE: Functional
COMPONENT: File System
STATEMENT: >>>
Zephyr shall provide file create capabilities for files on the file system
<<<
USER_STORY: >>>
As a Zephyr OS user I want to be able to create a new file or overwrite an existing file at the same filesystem location / identifier (e.g. path + name)
<<<
DISCUSSION_DATE: >>>
2022/4/13 - ok -pf
<<<

[REQUIREMENT]
TYPE: Functional
COMPONENT: File System
STATEMENT: >>>
Zephyr shall provide the capability to move files on the file system
<<<
DISCUSSION_DATE: >>>
- DIscuss implications of file operations and safety (how demonstrate that the system remains safe)
<<<

[REQUIREMENT]
TYPE: Functional
COMPONENT: File System
STATEMENT: >>>
Zephyr shall provide file delete capabilities for files on the file system
<<<
USER_STORY: >>>
As a Zephyr OS user I want to be able to delete an existing file.
<<<
DISCUSSION_DATE: >>>
2022/4/13 - ok -pf
<<<

[REQUIREMENT]
TYPE: Functional
COMPONENT: File System
STATEMENT: >>>
Zephyr shall provide read access to files in the file system
<<<
USER_STORY: >>>
As a Zephyr OS user I want to be able to read from an existing file, also while the file is read from multiple and write accessed from one other instances.
<<<
DISCUSSION_DATE: >>>
2022/4/13 - ok -pf
<<<

[REQUIREMENT]
TYPE: High Level
COMPONENT: Interrupts
TITLE: Interrupt Service Routine
STATEMENT: >>>
Zephyr shall provide a framework for interrupt management
<<<
USER_STORY: >>>
As a Zephyr OS user I want interrupts to be handled sychronously in response to a hardware or software interrupt request with a minimum latency, preemtping threads and, as far as the hardware allows, lower priority interrupt service routines.
<<<
DISCUSSION_DATE: >>>
2022/4/13 - ok - pf
<<<

[REQUIREMENT]
TYPE: Functional
COMPONENT: Interrupts
STATEMENT: >>>
Zephyr shall provide support a service routine for handling interrupts (ISR) .
<<<
USER_STORY: >>>
Duplicate to line 30? delete?
<<<
DISCUSSION_DATE: >>>
2022/4/13 - ok - pq
<<<

[REQUIREMENT]
TYPE: Functional
COMPONENT: Interrupts
TITLE: Multi-level interrupts
STATEMENT: >>>
Where supported by hardware, Zephyr shall support multi-level preemptive interrupt priorities, when supported by hardware.   Note:  detailed analysis to demonstrate non interferenace will be needed here.
<<<
USER_STORY: >>>
=N37
<<<
DISCUSSION_DATE: >>>
2022/4/13 - ok - pf
<<<

[REQUIREMENT]
TYPE: Functional
COMPONENT: Interrupts
TITLE: Associating application code with interrupts
STATEMENT: >>>
Zephyr shall provide an interface mechanisms for associating application code with specific interrupts.  ( CLARIFY: Can it be a deferred procedure call at interrupt context?  Would be different requirement)
<<<
USER_STORY: >>>
=N37
<<<
DISCUSSION_DATE: >>>
2022/4/13 - ok - pf
<<<

[REQUIREMENT]
TYPE: Functional
COMPONENT: Interrupts
STATEMENT: >>>
Zephyr shall provide mechanisms to enable interrupts
<<<
DISCUSSION_DATE: >>>
2022/8/29 - ok -pf
<<<

[REQUIREMENT]
TYPE: Functional
COMPONENT: Interrupts
TITLE: Enable and disable interrupts at runtime
STATEMENT: >>>
Zephyr shall provide mechanisms to disable interrupts
<<<
USER_STORY: >>>
As a Zephyr OS user I want to be able to enable and disable each individual and a global interrupt according to my applications needs during program execution.
<<<
DISCUSSION_DATE: >>>
2022/8/29 - ok -pf
<<<

[REQUIREMENT]
TYPE: High Level
COMPONENT: Logging
TITLE: Logging
STATEMENT: >>>
Zephyr shall provide a framework for logging events
<<<
USER_STORY: >>>
As a Zephyr OS user I want to be able to log application defined events as well as framework exceptions.
<<<
DISCUSSION_DATE: >>>
2022/4/13 - ok - pf
<<<
REVIEW_COMMENT: >>>
Nicole:  we need to have logging in the safety scope?
<<<

[REQUIREMENT]
TYPE: Functional
COMPONENT: Logging
TITLE: Dedicated Logging Thread Support
STATEMENT: >>>
Zephyr shall support isolation of logging from other functionality.
<<<
USER_STORY: >>>
As a Zephyr OS user I want to be able to configure logging of events so the execution of logging activities does have no or only a minimal impact to the timing behaviour of my application.
<<<
DISCUSSION_DATE: >>>
2022/4/13 - ok - pf
<<<

[REQUIREMENT]
TYPE: Functional
COMPONENT: Logging
STATEMENT: >>>
Zephyr logging shall produce logs that are capable of being post processed
<<<
USER_STORY: >>>
As a Zephyr OS user I want the logging information to be stored in a format which allows to be read possibly converted or displayed by COTS tools.
<<<
DISCUSSION_DATE: >>>
2022/4/13 - ok - pf
<<<

[REQUIREMENT]
TYPE: Functional
COMPONENT: Logging
STATEMENT: >>>
Zephyr logging shall support formatting of log messages to enable filtering
<<<
USER_STORY: >>>
As a Zephyr OS user I want to be able my application to format texts (printf alike) into the log message.
<<<
DISCUSSION_DATE: >>>
2022/10/25 - Incomplete - Need more information.  Specify format at this point.
<<<
REVIEW_COMMENT: >>>
Question: formatting in which way? length, color, tags, etc?
<<<

[REQUIREMENT]
TYPE: Functional
COMPONENT: Logging
TITLE: Logging Filtering Support
STATEMENT: >>>
Zephyr logging system shall support filtering based on severity level.
<<<
USER_STORY: >>>
As a Zephyr OS user I want to be able to distinguish between different severity level for my log messages (e.g. DEBUG, INFO, WARN, ERROR, PANIC)
<<<
DISCUSSION_DATE: >>>
2022/10/25 -ok
<<<
REVIEW_COMMENT: >>>
Question: Filtering during runtime or a kconfig option to initially set the filter for logging
<<<

[REQUIREMENT]
TYPE: Functional
COMPONENT: Logging
TITLE: Multiple Backend Logging Support
STATEMENT: >>>
Zephyr shall support logging messages to multiple hardware system resources
<<<
USER_STORY: >>>
As a Zephyr OS user I want to be able to simultaneously log to different channels which may store / redirect the information on / to different hardware (EEPROM, Flash, FRAM, UART, Ethernet, USB etc.)
<<<
DISCUSSION_DATE: >>>
2022/10/25 -ok
<<<
REVIEW_COMMENT: >>>
Question: What kind of backends shall be supported? More than one at a time?   Word choices.... backends/devices/channels/destinations/resources (devices, memory, ....) )
<<<

[REQUIREMENT]
TYPE: Functional
COMPONENT: Logging
TITLE: Deferred Logging Support
STATEMENT: >>>
Zephyr shall support deferred logging    (TODO: need more detail about the constraints and limits on what can be deferred)
<<<
USER_STORY: >>>
As a Zephyr OS user I want a minimal influence of logging activities to the timing behaviour of my application. Time consuming logging tasks shall be done in the background.
<<<
DISCUSSION_DATE: >>>
2022/10/25 -ok
<<<

[REQUIREMENT]
TYPE: High Level
COMPONENT: Memory Management
STATEMENT: >>>
Zephyr shall support a memory management framework
<<<
USER_STORY: >>>
As a Zephyr OS user I want memory to be allocated and protected to my application threads preventing mistakenly access to foreign memory as far as the hardware allows.
<<<
DISCUSSION_DATE: >>>
2022/10/25 - ok
<<<

[REQUIREMENT]
TYPE: Functional
COMPONENT: Memory Protection
TITLE: Memory Protection
STATEMENT: >>>
Zephyr shall support memory protection features to isolate a thread's memory region
<<<
USER_STORY: >>>
=N50
<<<
DISCUSSION_DATE: >>>
2022/10/25 - ok
<<<
REVIEW_COMMENT: >>>
Functional it is memory management, but it also strongly relates to the architecture abstraction and memory access
<<<

[REQUIREMENT]
TYPE: Functional
COMPONENT: Memory Objects
TITLE: Dynamic Memory Allocation
STATEMENT: >>>
Zephyr shall support a memory pool object that allow threads to dynamically allocate variable-sized memory regions from a specified range of memory region in a malloc()-like manner.
<<<
USER_STORY: >>>
As a Zephyr OS user I want my application to be able to dynamically allocate memory of a application defined size.
<<<
DISCUSSION_DATE: >>>
2022/10/25 - ok
<<<
REVIEW_COMMENT: >>>
Is dynamic memory allocation only allowed in memory pool objects?
<<<

[REQUIREMENT]
TYPE: Functional
COMPONENT: Memory Objects
TITLE: Memory Slab Object
STATEMENT: >>>
Zephyr shall support a memory slab object that allow threads to dynamically allocate fixed-sized memory regions from a specified range of memory.
<<<
USER_STORY: >>>
As a Zephyr OS user I want a most efficient and least fragmentation prone dynamic memory allocation mechanism.
<<<
DISCUSSION_DATE: >>>
2022/10/25 - ok
<<<

[REQUIREMENT]
TYPE: Functional
COMPONENT: Memory Protection
STATEMENT: >>>
Zephyr shall provide a mechanism to grant user threads access to kernel objects
<<<
USER_STORY: >>>
As a Zephyr OS user I want, from the user space, under certain condidtions, access to kernel objects
<<<
DISCUSSION_DATE: >>>
2022/10/25 - ok
<<<
REVIEW_COMMENT: >>>
What are the conditions to a user thread to get access to a kernel object?
<<<

[REQUIREMENT]
TYPE: Functional
COMPONENT: Memory Protection
STATEMENT: >>>
Zephyr shall be able to differentiate between user threads and kernel threads for memory access.
<<<
USER_STORY: >>>
As a Zephyr OS user I want, from the kernel space, unconditoned access to kernel objects.
<<<
DISCUSSION_DATE: >>>
2022/10/25 - ok
<<<

[REQUIREMENT]
TYPE: Functional
COMPONENT: Memory Protection
TITLE: Safely handle unimplemented calls or invalid system calls
STATEMENT: >>>
Zephyr shall safely handle invocations of unimplemented system calls or invalid system call IDs.   Zephyr shall have a defined behaviour when an invocation of an unimplemented system call is made.
<<<
USER_STORY: >>>
As a Zephyr OS user I want Zephyr OS to indicate any unimplemented system call by an appropriate error message.
<<<
DISCUSSION_DATE: >>>
2022/4/13 - ok - pq
<<<
REVIEW_COMMENT: >>>
What is an "unimplemented system call"? An empty system call function? Can I call something that is not there it all? Isn't this more a topic for security? - makes sense to handle this from the safety perspective, but still raises some quesitions here.
<<<

[REQUIREMENT]
TYPE: Functional
COMPONENT: Memory Protection
STATEMENT: >>>
Zephyr shall have a defined behavior when an invalid system call ID is used.
<<<
USER_STORY: >>>
As a Zephyr OS user I want Zephyr OS to indicate invalid system call by an appropriate error message.
<<<
DISCUSSION_DATE: >>>
2022/4/13 - ok - pq
<<<

[REQUIREMENT]
TYPE: Functional
COMPONENT: Memory Protection
TITLE: Prevent user threads creating higher priority threasds
STATEMENT: >>>
Zephyr shall prevent user threads from creating new threads that are higher priority than the caller.
<<<
USER_STORY: >>>
As a Zephyr OS user I want ... ???

(Sorry I still do not see the reason for such a requirement, if I, as a user, do not want to get swapped out of my thread creating thread, I can take care of that myself. If there are security (safety?) thought behind, it would be nice to understand them and document them here.)
<<<
DISCUSSION_DATE: >>>
2022/4/26 -ok - pq
<<<

[REQUIREMENT]
TYPE: Functional
COMPONENT: Memory Protection
TITLE: Revoking threads permissions on a kernel object
STATEMENT: >>>
Zephyr shall support revoking permission to a kernel object. User mode threads may only revoke their own access to an object.
<<<
USER_STORY: >>>
As a Zephyr OS user I want to be protected against other user threads changing access to kernel objects of my thread.
<<<
DISCUSSION_DATE: >>>
2022/10/25 - ok
<<<

[REQUIREMENT]
TYPE: Functional
COMPONENT: Memory Protection --> Thread
TITLE: Prevent user threads creating supervisor threads
STATEMENT: >>>
Zephyr shall prevent user threads from creating kernel supervisor threads.
<<<
USER_STORY: >>>
As a Zephyr OS user I want to be protected against user threads creating higher privileged kernel/supervisior threads.
<<<
DISCUSSION_DATE: >>>
2022/10/25 - ok
<<<

[REQUIREMENT]
TYPE: Functional
COMPONENT: Memory Protection --> Thread
TITLE: Reduced Privilege Level Threads
STATEMENT: >>>
Zephyr shall allow the creation of threads that run in reduced privilege level
<<<
USER_STORY: >>>
As a Zephyr OS user I want to be able to create lower privilegded threads than my own.
<<<
DISCUSSION_DATE: >>>
2022/4/26 -ok - pf
<<<

[REQUIREMENT]
TYPE: Functional
COMPONENT: Memory Protection
TITLE: User Mode Threads Performing Privileged Operations
STATEMENT: >>>
Zephyr shall provide system calls to allow user mode threads to perform privileged operations
<<<
USER_STORY: >>>
As a Zephyr OS user I want to be able to perform privileged operations in the kernel mode through a well defined interface.
<<<
DISCUSSION_DATE: >>>
2022/4/26 -ok - pq
<<<

[REQUIREMENT]
TYPE: Functional
COMPONENT: Memory Protection
TITLE: Stack Overflow Detection
STATEMENT: >>>
Zephyr shall support detection of stack overflows
<<<
USER_STORY: >>>
As a Zephyr OS user I want to get an indication when a stack overflow occurs at least during debugging / the development phase, and for safety applications also in a release version of my application.
<<<
DISCUSSION_DATE: >>>
2022/4/26 -reviewed.     Need to determine what to handle.   Well defined hooks?   Separate Requirement
<<<
REVIEW_COMMENT: >>>
RS: IMHO should be configurable due the to performance penalty introduced with it.   - DL:  THere are various modes,  canaries, and they can be turned off.  KS:  Clearly safety & security mechanism.
<<<

[REQUIREMENT]
TYPE: Functional
COMPONENT: Memory Protection
STATEMENT: >>>
Zephyr shall support a defined mechanism for user mode handling a of detected stack overflow
<<<
USER_STORY: >>>
As a Zephyr OS user I want, when a stack overlow is detected, to be able to implement a graceful, application defined handling of the exception.
<<<
DISCUSSION_DATE: >>>
2022/4/26 -pending  - potentially look at replacement term for handling.   If stack is blown, where can this exist - how does user mode access?
<<<
REVIEW_COMMENT: >>>
Need for handlers and callbacks outside of thread.   Need to be able to answer "Can the safety application rely on Zephyr to reach the safe state after stack overflow occured?"   Can it handle degredaded mode.
<<<

[REQUIREMENT]
TYPE: Functional
COMPONENT: Memory Protection
TITLE: Boot Time Memory Access Policy
STATEMENT: >>>
Zephyr shall support a boot time memory access policy.   Zephyr shall support configurable access to memory during boot time.
<<<
USER_STORY: >>>
As a Zephyr OS user I want... ???
<<<
DISCUSSION_DATE: >>>
2022/4/26 - need clarification from Anas (please provide pointers to implementation)
<<<
REVIEW_COMMENT: >>>
What does "policy" mean in this context? Does this mean to choose between different start up sequences?
<<<

[REQUIREMENT]
TYPE: Functional
COMPONENT: Memory Protection
TITLE: System Call Handler Functions
STATEMENT: >>>
Zephyr shall provide helper functions for system call handler functions to validate the inputs passed in from user mode before invoking the implementation function to protect the kernel
<<<
USER_STORY: >>>
As a Zephyr OS user I want Zepyhr OS to validate system call parameters passed from the user mode to the kernel mode to avoid crashes and undefined behaviour.
<<<
DISCUSSION_DATE: >>>
2022/4/26 - borderline (may want to revisit given that we've got questions).
<<<
REVIEW_COMMENT: >>>
I do not understand that. What kind of helper functions? Kind of plausibility checks? Does it make sense to provide this functionality on OS level?   David:  These are likely just validation that the parameters are not going to be dangerous (security/safety).
<<<

[REQUIREMENT]
TYPE: Functional
COMPONENT: Memory Protection
TITLE: System Call C strings in user mode
STATEMENT: >>>
Zephyr shall support system calls to be able to safely accept C strings passed in from user mode
<<<
USER_STORY: >>>
As a Zephyr OS user I want Zepyhr OS to validate system call string type parameters passed from the user mode to the kernel mode to avoid crashes and undefined behaviour.

e.g.

- verify the string length is smaller or equal to the syscalls defined max.
- verify that the length type does not overflow when allocating one more byte ???
<<<
DISCUSSION_DATE: >>>
2022/5/25 - subset of ZEP133?  Consider that 133 will cover.   Would like to see this against user stories.
<<<
REVIEW_COMMENT: >>>
Is this a helper function like mentioned in ZEP133? What does C string mean here? Like a string variable that's passed down from user mode to ??? by a system call?
<<<

[REQUIREMENT]
TYPE: Functional
COMPONENT: Memory Protection
TITLE: Tracking kernel objects in used by usermode threads
STATEMENT: >>>
Zephyr shall track kernel objects that are used by user mode threads

Note: this means Zephyr shall track the resources used by the user mode thread (associate this with a user story)
<<<
USER_STORY: >>>
I do not see a direct user story behind.

This is a sub-requirement to 102a,b,c.
and on architecture / interface level.
<<<
DISCUSSION_DATE: >>>
2022/5/25 - need to write down the user story associated with this.
<<<
REVIEW_COMMENT: >>>
Does this mean that the user mode threads are monitored wrt to their usage of kernel objects?  Example/User story would help.
<<<

[REQUIREMENT]
TYPE: Functional
COMPONENT: Memory Protection
TITLE: Granting threads access to specific memory
STATEMENT: >>>
Zephyr shall have mechanisms an interface to allow threads to request access to specific memory after initial allocation
<<<
USER_STORY: >>>
As a Zephyr OS user I want to be able to request read-only or read-write access to a dedicated memory area/pool during runtime.
<<<
DISCUSSION_DATE: >>>
2022/5/25 -  ok - pf
<<<
REVIEW_COMMENT: >>>
What is the difference to ZEP 011?
<<<

[REQUIREMENT]
TYPE: Functional
COMPONENT: Memory Protection
TITLE: Assigning memory pools to act as a thread resource pool
STATEMENT: >>>
Zephyr shall support assigning a memory pool to act as that thread's resource pool.
<<<
USER_STORY: >>>
As a Zephyr OS user I want to be able, during runtime from the kernel, to request a memory area/pool which is exclusively available to the requesting thread protected against access from other threads.
<<<
DISCUSSION_DATE: >>>
2022/5/25 - ok - pq
<<<
REVIEW_COMMENT: >>>
What is the difference to ZEP 136? Read & Write, while ZEP136 is just read?
<<<

[REQUIREMENT]
TYPE: Functional
COMPONENT: see: https://docs.zephyrproject.org/latest/reference/kernel/index.html - Data Passing
TITLE: Traditional FIFO Queue
STATEMENT: >>>
Zephyr shall provide a kernel object that implements a traditional first in, first out (FIFO) queue, allowing threads and ISRs to add and remove a limited number of 32-bit data values.
<<<
USER_STORY: >>>
As a Zephyr OS user I want to be able to exchange 1 to N data objects between different threads and ISR in a thread-safe manner with a first-in-first-out (queue) behaviour.
<<<
DISCUSSION_DATE: >>>
2022/5/25 - need to split appart into specific requirements.   Why call out 32-bit data values.  Need to generalize?   Why limited number?
<<<

[REQUIREMENT]
TYPE: Functional
COMPONENT: see: https://docs.zephyrproject.org/latest/reference/kernel/index.html - Data Passing
TITLE: Traditional LIFO queue
STATEMENT: >>>
Zephyr shall provide a kernel object that implements a traditional last in, first out (LIFO) queue, allowing threads and ISRs to add and remove a limited number of 32-bit data values.
<<<
USER_STORY: >>>
As a Zephyr OS user I want to be able to exchange 1 to N data objects between different threads and ISR in a thread-safe manner with a last-in-first-out (stack) behaviour
<<<
DISCUSSION_DATE: >>>
2022/5/25 - need to split appart into specific requirements.   Why call out 32-bit data values.  Need to generalize?   Why limited number?
<<<

[REQUIREMENT]
TYPE: Functional
COMPONENT: Mutex
TITLE: Mutex Kernel Object
STATEMENT: >>>
Zephyr shall support resource synchronization.   (Note synchronization can be for memory access, and mutex may be one implementation, but not the only one)
<<<
USER_STORY: >>>
As a Zephyr OS user I want to be able to sychonize threads when accessing common resources, where the thread shall have the option to
- wait eternally until the resources becomes available
- immediately return with a negative message if the resource is not available and allow the thread to continue
- wait for a given time for the resource to become available or return with a negative message.
<<<
DISCUSSION_DATE: >>>
2022/5/25 - ok
<<<
REVIEW_COMMENT: >>>
Concern over phrase recursive.  What is it MUTEXing? Memory Management?
<<<

[REQUIREMENT]
TYPE: High Level
COMPONENT: Power Management
TITLE: Power Management
STATEMENT: >>>
Zephyr shall provide an interface to control framework to provide support control over hardware power states
<<<
USER_STORY: >>>
As a Zephyr OS user I want to be able to control the power mode of the MCU and its peripherals to take advantage of the hardward features and to be able to implement low power or battery driven long life applications.
<<<
DISCUSSION_DATE: >>>
2022/5/25 - ok pf-ok
<<<

[REQUIREMENT]
TYPE: Functional
COMPONENT: Power Management
TITLE: Power State Control
STATEMENT: >>>
Zephyr shall provide control over changes to system power states.
<<<
USER_STORY: >>>
See ZEP104
+
When the power state is changed I want to get an notification in order for specific parts of my application to react accodingly.
<<<
DISCUSSION_DATE: >>>
2022/5/25 - split into two requirements.
<<<

[REQUIREMENT]
TYPE: Functional
COMPONENT: Power Management
DISCUSSION_DATE: >>>
2022/8/23 - figure out what capabilities are working here today.
<<<

[REQUIREMENT]
TYPE: Functional
COMPONENT: Power Management
STATEMENT: >>>
Zephyr shall provide notification of changes to system power states.
<<<
DISCUSSION_DATE: >>>
2022/8/23 - split out from 114.
<<<

[REQUIREMENT]
TYPE: High Level
COMPONENT: Thread Communication
TITLE: Mutex
STATEMENT: >>>
Zephyr shall provide an interface framework for managing communcation between threads.
<<<
USER_STORY: >>>
As a Zephyr OS user I want to able to exchange information between threads in a thread-safe manner guaranteeing data consistence.
<<<
DISCUSSION_DATE: >>>
2022/5/25 - ok  - pf-ok
<<<

[REQUIREMENT]
TYPE: Functional
COMPONENT: Thread Communication
TITLE: Mailbox
STATEMENT: >>>
Zephyr shall provide mechanisms for thread synchronization for managing safe communication between threads and to enable waiting for results
<<<
USER_STORY: >>>
=N78 & "

+
What does safe mean, I would not consider safe as in safety"
<<<
DISCUSSION_DATE: >>>
2022/5/25 - need a definition of what is "safe communication"
<<<

[REQUIREMENT]
TYPE: Functional
COMPONENT: Thread Communication
STATEMENT: >>>
Zephyr shall provide a mechanism for exchanging data between threads.
<<<
USER_STORY: >>>
(Note: copying data may be needed here - what is Zephyr doing? is it configurable?)
<<<
DISCUSSION_DATE: >>>
2022/8/23 - pf-ok
<<<

[REQUIREMENT]
TYPE: Functional
COMPONENT: Thread Communication
STATEMENT: >>>
Zephyr shall provide mechanisms to enable waiting for results during communication between threads.   (NOTE:  waiting for results is really bad and dangerous, want to avoid if at all possible)
<<<
USER_STORY: >>>
=N73
<<<
DISCUSSION_DATE: >>>
2022/5/25 - ok
<<<

[REQUIREMENT]
TYPE: Functional
COMPONENT: Thread Communication
TITLE: Stack
STATEMENT: >>>
The Zephyr kernel shall provide a stack
<<<
USER_STORY: >>>
As a Zephyr OS user I want to... ???,
<<<
DISCUSSION_DATE: >>>
2022/5/25 - needs to be clarified what stack refers to
<<<
REVIEW_COMMENT: >>>
stack of what?
<<<

[REQUIREMENT]
TYPE: Functional
COMPONENT: Thread Communication
TITLE: Traditional Counting Semaphore
STATEMENT: >>>
Zephyr shall provide a counting semaphore abstraction for queuing and mutual exclusion.
<<<
USER_STORY: >>>
As a Zephyr OS user I want to... ???,

Architectural & interface REQ
<<<

[REQUIREMENT]
TYPE: Functional
COMPONENT: Thread Communication
TITLE: Poll Operation Support
STATEMENT: >>>
Zephyr shall support a poll operation which enables waiting concurrently for any one of multiple conditions to be fulfilled.
<<<
USER_STORY: >>>
As a Zephyr OS user I want my thread to wait for one of several defined events to occur and only continue when one of them has occured.
<<<

[REQUIREMENT]
TYPE: Functional
COMPONENT: Thread Communication
TITLE: Pipe Kernel Object
STATEMENT: >>>
Zephyr shall provide a kernel object that allows a thread to transfer a block of data a byte stream to another thread.
<<<
USER_STORY: >>>
As a Zephyr OS user I want to send a byte stream from one thread to another in a thread-safe manner.
<<<
DISCUSSION_DATE: >>>
2022/8/23 pq - are we copying it, or just transfering control over it.   Why important kernel object?
<<<

[REQUIREMENT]
TYPE: Functional
COMPONENT: Thread Communication
TITLE: Message Queue Kernel Object
STATEMENT: >>>
Zephyr shall provide a kernel object that implements a simple message queue, allowing threads and ISRs to asynchronously send and receive fixed-size data items.
<<<
USER_STORY: >>>
=N71 & "

(from K68)"
<<<
REVIEW_COMMENT: >>>
This might be too implementation specific. Better: Zephyr shall allow threads and ISRs to asynchronously exchange fixed-size data items.
<<<

[REQUIREMENT]
TYPE: Functional
COMPONENT: Thread Communication
TITLE: Mailbox Abstraction
STATEMENT: >>>
Zephyr shall support a mailbox abstraction to enable targeted message passing between threads.
<<<
USER_STORY: >>>
As a Zephyr OS user I want to... ???
<<<

[REQUIREMENT]
TYPE: High Level
COMPONENT: Thread Mapping (should it just be scheduling)
TITLE: Multiple CPU scheduling
STATEMENT: >>>
Zephyr shall support scheduling of OS threads on multiple hardware CPUs
<<<
USER_STORY: >>>
As a Zephyr OS user I want Zephyr OS to run on MCUs/CPUs with one or more CPU cores.
<<<
DISCUSSION_DATE: >>>
pf-ok
<<<

[REQUIREMENT]
TYPE: Functional
COMPONENT: Thread Mapping (should it just be scheduling) -
TITLE: Support operation on more than one CPU
STATEMENT: >>>
The Zephyr kernel shall support operation on more than one physical CPU sharing the same kernel state
<<<
USER_STORY: >>>
As a Zephyr OS user I want to ...???

Is see it as an internal hidden from the user.
<<<

[REQUIREMENT]
TYPE: Functional
COMPONENT: Thread Mapping (should it just be scheduling)
TITLE: Running threads on specific CPUs
STATEMENT: >>>
Zephyr shall provide an interface mechanism for running threads on specific sets of CPUs ( default is 1 CPU).
<<<
USER_STORY: >>>
As a Zephyr OS user I want Zephyr OS to be able to specify the CPU core or the set of CPU cores on which a thead shall be executed.
<<<
DISCUSSION_DATE: >>>
pf-ok
<<<

[REQUIREMENT]
TYPE: Functional
COMPONENT: Thread Mapping (should it just be scheduling?)
TITLE: Exclusion between physical CPUs
STATEMENT: >>>
Zephyr shall provide an interface mechanism for mutual exclusion between multiple physical CPUs using a spinlock primitive.
<<<
USER_STORY: >>>
As a Zephyr OS user I want Zephyr OS to provide synchonization mechanisms between the CPU cores and the access to common resources.
<<<
DISCUSSION_DATE: >>>
pf-ok
<<<

[REQUIREMENT]
UID: ZEP-SCHED-001
TYPE: High Level
COMPONENT: Thread Scheduling
TITLE: Scheduling
STATEMENT: >>>
Zephyr shall provide a mechanism for selecting which of many threads will be run on a given CPU   Zephyr shall provide an interface to assign a thread to a specific CPU.
<<<
USER_STORY: >>>
As a Zephyr OS user, I want to be able to control which thread will run on which CPU
<<<
DISCUSSION_DATE: >>>
pf-ok
<<<
REVIEW_COMMENT: >>>
Zephyr shall allow scheduling of threads
<<<

[REQUIREMENT]
UID: ZEP-SCHED-002
TYPE: Functional
COMPONENT: Thread Scheduling
STATEMENT: >>>
Zephyr shall provide an interface to create (start) a thread
<<<
DISCUSSION_DATE: >>>
pf-ok
<<<

[REQUIREMENT]
TYPE: Functional
COMPONENT: Thread Scheduling
STATEMENT: >>>
Zephyr shall provide an interface to set a thread's priority
<<<
DISCUSSION_DATE: >>>
pf-ok
<<<

[REQUIREMENT]
TYPE: Functional
COMPONENT: Thread Scheduling
STATEMENT: >>>
Zephyr shall provide an interface to suspend a thread
<<<
DISCUSSION_DATE: >>>
pf-ok
<<<

[REQUIREMENT]
TYPE: Functional
COMPONENT: Thread Scheduling
STATEMENT: >>>
Zephyr shall provide an interface to resume a suspended thread
<<<
DISCUSSION_DATE: >>>
pf-ok
<<<

[REQUIREMENT]
STATEMENT: >>>
Zephyr shall provide an interface to resume a suspended thread after a timeout
<<<
DISCUSSION_DATE: >>>
pf-ok
<<<

[REQUIREMENT]
TYPE: Functional
COMPONENT: Thread Scheduling
STATEMENT: >>>
Zephyr shall provide an interface to delete (end) a thread
<<<
DISCUSSION_DATE: >>>
pf-ok
<<<

[REQUIREMENT]
TYPE: Functional
COMPONENT: Thread Scheduling
STATEMENT: >>>
 Zephyr shall provide an interface to schedule a thread based on an event
<<<
USER_STORY: >>>
As a Zephyr OS user, I want to be able to execute work which reacts on events and interrupts the current executed work
<<<
DISCUSSION_DATE: >>>
pf-ok
<<<

[REQUIREMENT]
TYPE: Functional
COMPONENT: Thread Scheduling
TITLE: Meta-IRQ Priorities
STATEMENT: >>>
The Zephyr kernel shall support running threads in Meta-IRQ Priorities
<<<
USER_STORY: >>>
TBD Page is not available anymore
<<<
REVIEW_COMMENT: >>>
Does this make sense in the safety scope? It is conflicting with ZEP151.
<<<

[REQUIREMENT]
TYPE: Functional
COMPONENT: Thread Scheduling
TITLE: Deadline Scheduling Priorities
STATEMENT: >>>
Zephyr shall organize running threads by earliest deadline first priority.
<<<
USER_STORY: >>>
As a Zephyr OS user, I want to be able to schedule threads by earliest deadine first
<<<

[REQUIREMENT]
TYPE: Functional
COMPONENT: Thread Scheduling
TITLE: Work Queue utility capable of running preemptible work items
STATEMENT: >>>
Zephyr shall provide a thread-pooled work queue utility capable of running preemptible work items with specific scheduler priorities.
<<<
USER_STORY: >>>
As a Zephyr OS user, I want to be able to add work items in a thread work queue with different priorities and these shall be scheduled accoding their priorities
<<<
DISCUSSION_DATE: >>>
Implementation detail.   Consider as a sub requirent?   Why do we need this?
<<<

[REQUIREMENT]
UID: ZEP-SCHED-#
TYPE: Functional
COMPONENT: Thread Scheduling
TITLE: Run user supplied functions in-order in a separate thread(s)
STATEMENT: >>>
Zephyr shall provide an interface for running user-supplied functions.  a work queue mechanism for running user-supplied functions ("work items") in-order in a separate thread or threads
<<<
USER_STORY: >>>
As a Zephyr OS user, I want to be able to run functions in-order in a sperated thread/threads
<<<
DISCUSSION_DATE: >>>
pf-ok
<<<
REVIEW_COMMENT: >>>
Where do we put this,  thread, scheduling or???
<<<

[REQUIREMENT]
TYPE: Functional
COMPONENT: Thread Scheduling
TITLE: Organize running threads into a fixed list
STATEMENT: >>>
Zephyr shall organize running threads into a fixed list of numeric priorities   (see: https://docs.zephyrproject.org/latest/kernel/services/threads/index.html#thread-priorities)
<<<
USER_STORY: >>>
As a Zephyr OS user, I want that the OS organize running threads in a fixed list of numeric priorities
<<<
DISCUSSION_DATE: >>>
Why is this an external requirement?    Implementation detail.
<<<
REVIEW_COMMENT: >>>
Zephyr shall allow priorising threads
<<<

[REQUIREMENT]
TYPE: Functional
COMPONENT: Thread Scheduling
TITLE: Preemption support
STATEMENT: >>>
Zephyr shall support preemption of a running thread by a higher priority thread
<<<
USER_STORY: >>>
As a Zephyr OS user, I want that the OS preempt running threads by a thread with higher priority
<<<
DISCUSSION_DATE: >>>
Need to break this down to atomic level
<<<

[REQUIREMENT]
TYPE: Functional
COMPONENT: Thread Scheduling
TITLE: Un-preemptable thread priorities
STATEMENT: >>>
Zephyr shall support thread priorities which cannot be preempted by other user threads.
<<<
USER_STORY: >>>
As a Zephyr OS user, I want to be able to configure thread prioriteies which cannot be preempted by other user threads
<<<
DISCUSSION_DATE: >>>
Need to break this down to atomic level
<<<

[REQUIREMENT]
TYPE: Functional
COMPONENT: Thread Scheduling
TITLE: Time sharing of CPU resources
STATEMENT: >>>
Zephyr shall support traditional time sharing of CPU resources among threads of the same priority.
<<<
USER_STORY: >>>
As a Zephyr OS user, I want to be able to onfigure my RTOS in the way, that the CPU resources are shared evenly among executed threads of the same priority
<<<
DISCUSSION_DATE: >>>
What does traditional mean?   Need to be specific
<<<
REVIEW_COMMENT: >>>
what does traditional mean here?   Round robin?
<<<

[REQUIREMENT]
UID: ZEP-THREAD-001
TYPE: High Level
COMPONENT: Threads
TITLE: Managing threads
STATEMENT: >>>
Zephyr shall provide a framework facilities for managing multiple threads of execution.
<<<
USER_STORY: >>>
As a Zephyr OS user, I want to be able to manage the execute of multiple threads with different priorities
<<<
DISCUSSION_DATE: >>>
pf-ok
<<<
REVIEW_COMMENT: >>>
Nothing about priorities...
<<<

[REQUIREMENT]
TYPE: Functional
COMPONENT: Threads
TITLE: Thread Support
STATEMENT: >>>
Zephyr shall support multiple threads of execution
<<<
USER_STORY: >>>
As a Zephyr OS user, I want to be able to execute multiple threads which are managed by priorities or other mechanisms
<<<
DISCUSSION_DATE: >>>
pf-pq
<<<
REVIEW_COMMENT: >>>
Mechanism for this is mutex; so just link this here as well as others
<<<

[REQUIREMENT]
UID: ZEP-THREAD-002
TYPE: Functional
COMPONENT: Threads
STATEMENT: >>>
Zephyr shall provide an interface to create theads with defined privilege
<<<
DISCUSSION_DATE: >>>
pf-ok
<<<

[REQUIREMENT]
UID: ZEP-THREAD-003
TYPE: Functional
COMPONENT: Threads
STATEMENT: >>>
Zephyr shall provide an interface to schedule multiple threads
<<<
DISCUSSION_DATE: >>>
pf-ok
<<<

[REQUIREMENT]
TYPE: Functional
COMPONENT: Threads
STATEMENT: >>>
??? Can Zephyr change priviledge level of a thread once created??
<<<
DISCUSSION_DATE: >>>
TBD
<<<

[REQUIREMENT]
UID: ZEP-TIME-001
TYPE: High Level
COMPONENT: Timers
TITLE: Timers
STATEMENT: >>>
Zephyr shall provide a framework abstraction for managing time-based events
<<<
USER_STORY: >>>
As a Zephyr OS user, I want to start, suspend, resume and stop timers which shall trigger an event on a set expiration time
<<<
DISCUSSION_DATE: >>>
pf-ok
<<<
REVIEW_COMMENT: >>>
Do we need requirements on scheduling latency?
<<<

[REQUIREMENT]
UID: ZEP-TIME-002
TYPE: Functional
COMPONENT: Timers
REFS:
- TYPE: Parent
  VALUE: ZEP-TIME-001
TITLE: Kernel Clock
STATEMENT: >>>
Zephyr shall provide a interface for checking the current value of the real-time clock
<<<
USER_STORY: >>>
As a Zephyr OS user, I want to be able to track the passed real time in the OS with a dedicated hardware counter and interrupt
<<<
DISCUSSION_DATE: >>>
pf-ok
<<<

[REQUIREMENT]
UID: ZEP-TIME-003
TYPE: Functional
COMPONENT: Timers
REFS:
- TYPE: Parent
  VALUE: ZEP-TIME-001
TITLE: Call functions in interrupt context
STATEMENT: >>>
Zephyr shall provide an interface to allow schedule user mode call back function triggered by a real time clock value   provide a facility to call user-provided functions in interrupt context based on a system-maintained real-time hardware counter.
<<<
USER_STORY: >>>
As a Zephyr OS user, I want to be able to execute functions in the interrupt context and the interrupt context shall be base on a real-time counter
<<<
DISCUSSION_DATE: >>>
pf-ok
<<<

[REQUIREMENT]
UID: ZEP-TRACE-001
TYPE: High Level
COMPONENT: Tracing
TITLE: Tracing
STATEMENT: >>>
Zepyhr shall provide a framework mechanism for tracing low level system operations  (NOTE: system calls, interrupts, kernel calls, thread, synchronization, etc.)
<<<
USER_STORY: >>>
As a Zephyr OS user, I want to be able to trace different OS operations
<<<
DISCUSSION_DATE: >>>
Moved
<<<
REVIEW_COMMENT: >>>
What are low level system operations in this context?
<<<

[REQUIREMENT]
UID: ZEP-TRACE-002
TYPE: Functional
COMPONENT: Tracing
STATEMENT: >>>
Zephyr shall provide an interface to initialize a trace.
<<<
DISCUSSION_DATE: >>>
pf-ok
<<<

[REQUIREMENT]
UID: ZEP-TRACE-003
TYPE: Functional
COMPONENT: Tracing
STATEMENT: >>>
Zephyr shall provide an interface to trigger a trace.
<<<
DISCUSSION_DATE: >>>
pf-ok
<<<

[REQUIREMENT]
UID: ZEP-TRACE-004
TYPE: Functional
COMPONENT: Tracing
STATEMENT: >>>
Zephyr shall provide an interface to dump results from a trace.
<<<
DISCUSSION_DATE: >>>
pf-ok
<<<

[REQUIREMENT]
UID: ZEP-TRACE-005
TYPE: Functional
COMPONENT: Tracing
STATEMENT: >>>
Zephyr shall provide an interface to remove trace data.
<<<
DISCUSSION_DATE: >>>
pf-ok
<<<

[REQUIREMENT]
UID: ZEP-TRACE-006
TYPE: Functional
COMPONENT: Tracing
TITLE: Tracing Object  Identification
STATEMENT: >>>
Zephyr shall provide an interface to identify the objects being traced.
<<<
USER_STORY: >>>
As a Zepyhr OS user, I want to be able to give each object which I create a name / label in order to be able to identify them in a trace log.
<<<
DISCUSSION_DATE: >>>
pf-ok
<<<
REVIEW_COMMENT: >>>
What objects?   hardware devices, code, ....
<<<

[REQUIREMENT]
UID: ZEP-TRACE-007
TYPE: Functional
COMPONENT: Tracing
TITLE: Tracing Non-Interference
STATEMENT: >>>
Zepyhr shall prevent not allow the tracing functionality from interfering with normal operations of the operating system.
<<<
USER_STORY: >>>
As a Zepyhr OS user, I want that the trace functionality do not interfere or slow down the operation system functionality
<<<
DISCUSSION_DATE: >>>
pf-ok
<<<
REVIEW_COMMENT: >>>
What are "normal" operations? Might make sense to rephrase this to "any other operation"
<<<
