[DOCUMENT]
TITLE: Zephyr Functional Requirements
REQ_PREFIX: ZEP-

[GRAMMAR]
ELEMENTS:
- TAG: REQUIREMENT
  FIELDS:
  - TITLE: UID
    TYPE: String
    REQUIRED: False
  - TITLE: STATUS
    TYPE: String
    REQUIRED: False
  - TITLE: TYPE
    TYPE: String
    REQUIRED: False
  - TITLE: COMPONENT
    TYPE: String
    REQUIRED: False
  - TITLE: TITLE
    TYPE: String
    REQUIRED: False
  - TITLE: STATEMENT
    TYPE: String
    REQUIRED: False
  - TITLE: USER_STORY
    TYPE: String
    REQUIRED: False
  - TITLE: REVIEW_COMMENT
    TYPE: String
    REQUIRED: False
  RELATIONS:
  - TYPE: Parent

[SECTION]
TITLE: Hardware Architecture Interface

[REQUIREMENT]
UID: ZEP-8
STATUS: Draft
TYPE: Functional
COMPONENT: Hardware Architecture Interface
TITLE: Atomic Operations
STATEMENT: >>>
The Zephyr RTOS shall provide an interface functionality to access memory while ensuring mutual exclusion. Note: Implementation by atomic variables and accessing them by APIs.
<<<
USER_STORY: >>>
As a Zephyr RTOS user I want to read from or write into a memory areas without being disturbed by other threads or ISRs.
<<<
RELATIONS:
- TYPE: Parent
  VALUE: ZEP-1

[REQUIREMENT]
UID: ZEP-9
STATUS: Draft
TYPE: Functional
COMPONENT: Hardware Architecture Interface
TITLE: Thread Context Switching
STATEMENT: >>>
The Zephyr RTOS shall provide a mechanism for context switching between threads.
<<<
USER_STORY: >>>
As a Zephyr RTOS user I want to execute code concurrently in one or more threads and when interrupted at a code location in a thread, to continue at the very same location.
<<<
RELATIONS:
- TYPE: Parent
  VALUE: ZEP-1

[REQUIREMENT]
UID: ZEP-10
STATUS: Draft
TYPE: Functional
COMPONENT: Hardware Architecture Interface
TITLE: Software Exceptions
STATEMENT: >>>
The Zephyr RTOS shall provide an interface to implement software exceptions.
<<<
USER_STORY: >>>
As a Zephyr RTOS user I want to catch any software exception and handle it according to my application needs.
<<<
RELATIONS:
- TYPE: Parent
  VALUE: ZEP-1

[REQUIREMENT]
UID: ZEP-11
STATUS: Draft
TYPE: Functional
COMPONENT: Hardware Architecture Interface
TITLE: Processor Mode Support
STATEMENT: >>>
The Zephyr RTOS shall provide an interface for managing processor modes.
<<<
USER_STORY: >>>
If MCU power state was meant here:
As a Zephyr RTOS user I want to control the MCU's power saving mode such e.g. operation, sleep, deep sleep or similar as supported by the selected MCU.
<<<
REVIEW_COMMENT: >>>
What is life cycle - power on, standby, power off?  or ????

Clarification: Starting and Stopping, and putting it into Stand-By Mode (whatever the processor supports)
<<<
RELATIONS:
- TYPE: Parent
  VALUE: ZEP-1

[/SECTION]

[SECTION]
TITLE: C library

[REQUIREMENT]
UID: ZEP-12
STATUS: Draft
TYPE: Functional
COMPONENT: C Library
TITLE: Formatted output
STATEMENT: >>>
The Zephyr RTOS shall support formatted output.
<<<
USER_STORY: >>>
As a Zephyr RTOS user, I want to be able to printf with various output formats.
<<<
RELATIONS:
- TYPE: Parent
  VALUE: ZEP-2

[REQUIREMENT]
UID: ZEP-13
STATUS: Draft
TYPE: Functional
COMPONENT: C Library
TITLE: Floating Point Math Support
STATEMENT: >>>
The Zephyr RTOS shall support floating point math libraries for processors where floating point is available.
<<<
USER_STORY: >>>
As a Zephyr RTOS user, I want to be able to calculate with floating point numbers.
<<<
RELATIONS:
- TYPE: Parent
  VALUE: ZEP-2

[REQUIREMENT]
UID: ZEP-14
STATUS: Draft
TYPE: Functional
COMPONENT: C Library
TITLE: Boolean Primitives Support
STATEMENT: >>>
The Zephyr RTOS shall support boolean primitives.
<<<
USER_STORY: >>>
As a Zephyr RTOS user, I want to be able to work with boolean values and logic.
<<<
RELATIONS:
- TYPE: Parent
  VALUE: ZEP-2

[REQUIREMENT]
UID: ZEP-15
STATUS: Draft
TYPE: Functional
COMPONENT: C Library
TITLE: Standard Unix time interface
STATEMENT: >>>
The Zephyr RTOS shall support the standard UNIX time interface.
<<<
USER_STORY: >>>
As a Zephyr User, I want to be able to use system time.
<<<
RELATIONS:
- TYPE: Parent
  VALUE: ZEP-2

[REQUIREMENT]
UID: ZEP-16
STATUS: Draft
TYPE: Functional
COMPONENT: C Library
TITLE: Strings support
STATEMENT: >>>
The Zephyr RTOS shall support an interface to manage strings.
<<<
USER_STORY: >>>
As a Zephyr RTOS user, I want to be able to manipulate text strings.
<<<
RELATIONS:
- TYPE: Parent
  VALUE: ZEP-2

[REQUIREMENT]
UID: ZEP-17
STATUS: Draft
TYPE: Functional
COMPONENT: C Library
TITLE: Moving/copying regions of memory
STATEMENT: >>>
The Zephyr RTOS shall support an interface to move contents between regions of memory.
<<<
USER_STORY: >>>
As a Zephyr RTOS user, I want to copy the memory contents to different addresses.
<<<
RELATIONS:
- TYPE: Parent
  VALUE: ZEP-2

[REQUIREMENT]
UID: ZEP-18
STATUS: Draft
TYPE: Functional
COMPONENT: C Library
TITLE: I/O based interface
STATEMENT: >>>
The Zephyr RTOS shall support a file i/O based interface for driver communication.
<<<
USER_STORY: >>>
As a Zephyr RTOS user, I want to be able to use File I/O functions.
<<<
REVIEW_COMMENT: >>>
A wrong C header seems to be included: stdint.h does not have to do with I/O.
<<<
RELATIONS:
- TYPE: Parent
  VALUE: ZEP-2

[REQUIREMENT]
UID: ZEP-19
STATUS: Draft
TYPE: Functional
COMPONENT: C Library
TITLE: C99 integer types
STATEMENT: >>>
The Zephyr RTOS shall support standard C99 integer types.
<<<
USER_STORY: >>>
As a Zephyr RTOS user, I want to be able to calculate with C99 Integers.
<<<
RELATIONS:
- TYPE: Parent
  VALUE: ZEP-2

[REQUIREMENT]
UID: ZEP-20
STATUS: Draft
TYPE: Functional
COMPONENT: C Library
TITLE: Standard System Error Numbers (IEEE Std 1003.1-2017)
STATEMENT: >>>
The Zephyr RTOS shall support standard system error numbers as defined by IEEE Std 1003.1-2017.
<<<
USER_STORY: >>>
As a Zephyr RTOS user, I want to be able to use IEE Std 1003.1-2017 Error Numbers for Interoperability.
<<<
RELATIONS:
- TYPE: Parent
  VALUE: ZEP-2

[REQUIREMENT]
UID: ZEP-21
STATUS: Draft
TYPE: Functional
COMPONENT: C Library
TITLE: Document set of Zephyr OS required C library functions in Safety Manual
STATEMENT: >>>
The set of C Library functions required by Zephyr needs to be documented in the Zephyr Safety Manual.
<<<
USER_STORY: >>>
As a Zephyr user, I want to know which C library functions are being called by the Zephyr OS safety scope code.
<<<
RELATIONS:
- TYPE: Parent
  VALUE: ZEP-2

[REQUIREMENT]
UID: ZEP-22
STATUS: Draft
TYPE: Functional
COMPONENT: C Library
TITLE: Support external C libraries documentation in Zephyr Safety Manual
STATEMENT: >>>
The Zephyr Safety Manual needs to specify how to configure the support of external C Libraries.
<<<
USER_STORY: >>>
As a Zephyr User, I need to understand how to configure the external C libraries to align with the validation that has been performed.
<<<
RELATIONS:
- TYPE: Parent
  VALUE: ZEP-2

[/SECTION]

[SECTION]
TITLE: Device Driver API

[REQUIREMENT]
UID: ZEP-45
STATUS: Draft
TYPE: Functional
COMPONENT: Device Driver API
TITLE: Device Driver Abstraction
STATEMENT: >>>
The Zephyr RTOS shall provide abstraction of device drivers with common functionalities as an intermediate interface between applications and device drivers, where such interface is implemented by individual device drivers.

Proposal for replacement: Zephyr shall provide an interface between application and individual device drivers to provide an abstraction of device drivers with common functionalities.
<<<
REVIEW_COMMENT: >>>
What are common functionalities?

Clarification: Abstract API drivers, UART. Set of files associated with that. Include drivers. 50+ files. Best place to look at is the documentation (not the files).
<<<

[REQUIREMENT]
UID: ZEP-46
STATUS: Draft
TYPE: Functional
COMPONENT: Device Driver API
TITLE: Expose kernel to hardware interrupts
STATEMENT: >>>
The Zephyr RTOS shall provide an interface for managing a defined set of hardware exceptions (including interrupts) across all systems.
<<<
USER_STORY: >>>
As a Zephyr RTOS user I want hardware exceptions (hardware failures, programming mistakes) to be handled gracefully (no program crashes as far as possible).
<<<
REVIEW_COMMENT: >>>
What does "system" mean in this context? Architecture?

NP: Now I think system means HW platform.
<<<

[/SECTION]

[SECTION]
TITLE: Exception and Error Handling

[REQUIREMENT]
UID: ZEP-47
STATUS: Draft
TYPE: Functional
COMPONENT: Exception and Error Handling
TITLE: Fatal Exception Error Handler
STATEMENT: >>>
The Zephyr RTOS shall provide default handlers for exceptions.
<<<
USER_STORY: >>>
As a Zephyr RTOS user I want exceptions which I did not handle explicitly (by mistake or on purpose) to be caught by a default handler, defined either by Zephyr OS or by myself.
<<<

[REQUIREMENT]
UID: ZEP-48
STATUS: Draft
TYPE: Functional
COMPONENT: Exception and Error Handling
TITLE: Default handler for fatal errors
STATEMENT: >>>
The Zephyr RTOS shall provide default handlers for fatal errors that do not have a dedicated handler.
<<<

[REQUIREMENT]
UID: ZEP-49
STATUS: Draft
TYPE: Functional
COMPONENT: Exception and Error Handling
TITLE: Assigning a specific handler
STATEMENT: >>>
The Zephyr RTOS shall provide an interface to assign a specific handler with an exception.
<<<

[REQUIREMENT]
UID: ZEP-50
STATUS: Draft
TYPE: Functional
COMPONENT: Exception and Error Handling
TITLE: Assigning a specific handler (2)
STATEMENT: >>>
The Zephyr RTOS shall provide an interface to assign a specific handler for a fatal error.
<<<

[/SECTION]

[SECTION]
TITLE: File System

[REQUIREMENT]
UID: ZEP-51
STATUS: Draft
TYPE: Functional
COMPONENT: File System
TITLE: Create file
STATEMENT: >>>
The Zephyr RTOS shall provide file create capabilities for files on the file system.
<<<
USER_STORY: >>>
As a Zephyr RTOS user I want to be able to create a new file or overwrite an existing file at the same file system location / identifier (e.g. path + name).
<<<

[REQUIREMENT]
UID: ZEP-52
STATUS: Draft
TYPE: Functional
COMPONENT: File System
TITLE: Open files
STATEMENT: >>>
The Zephyr RTOS shall provide file open capabilities for files on the file system.
<<<
USER_STORY: >>>
As a Zephyr RTOS user I want to be able to open a file for writing or reading.
When opened for writing, I want to have exclusive access to the file.
<<<

[REQUIREMENT]
UID: ZEP-53
STATUS: Draft
TYPE: Functional
COMPONENT: File System
TITLE: Read files
STATEMENT: >>>
The Zephyr RTOS shall provide read access to files in the file system.
<<<
USER_STORY: >>>
As a Zephyr RTOS user I want to be able to read from an existing file, also while the file is read from multiple and write accessed from one other instances.
<<<

[REQUIREMENT]
UID: ZEP-54
STATUS: Draft
TYPE: Functional
COMPONENT: File System
TITLE: Write to files
STATEMENT: >>>
The Zephyr RTOS shall provide write access to the files in the file system.
<<<
USER_STORY: >>>
As a Zephyr RTOS user I want to be able to write to a file either from the beginning of the file or appending at the end.
<<<

[REQUIREMENT]
UID: ZEP-55
STATUS: Draft
TYPE: Functional
COMPONENT: File System
TITLE: Close file
STATEMENT: >>>
The Zephyr RTOS shall provide file close capabilities for files on the file system.
<<<
USER_STORY: >>>
As a Zephyr RTOS user I want to be able to close a file after being finished with my file operations, unlocking any access restrictions.
<<<

[REQUIREMENT]
UID: ZEP-56
STATUS: Draft
TYPE: Functional
COMPONENT: File System
TITLE: Move file
STATEMENT: >>>
The Zephyr RTOS shall provide the capability to move files on the file system.
<<<

[REQUIREMENT]
UID: ZEP-57
STATUS: Draft
TYPE: Functional
COMPONENT: File System
TITLE: Delete file
STATEMENT: >>>
The Zephyr RTOS shall provide file delete capabilities for files on the file system.
<<<
USER_STORY: >>>
As a Zephyr RTOS user I want to be able to delete an existing file.
<<<

[/SECTION]

[SECTION]
TITLE: Interrupts

[REQUIREMENT]
UID: ZEP-58
STATUS: Draft
TYPE: Functional
COMPONENT: Interrupts
TITLE: Service routine for handling interrupts (ISR)
STATEMENT: >>>
The Zephyr RTOS shall provide support a service routine for handling interrupts (ISR).
<<<

[REQUIREMENT]
UID: ZEP-59
STATUS: Draft
TYPE: Functional
COMPONENT: Interrupts
TITLE: Multi-level interrupts
STATEMENT: >>>
The Zephyr RTOS shall support multi-level preemptive interrupt priorities, when supported by hardware. Note: detailed analysis to demonstrate non interference will be needed here.
<<<

[REQUIREMENT]
UID: ZEP-60
STATUS: Draft
TYPE: Functional
COMPONENT: Interrupts
TITLE: Associating application code with interrupts
STATEMENT: >>>
The Zephyr RTOS shall provide an interface for associating application code with specific interrupts. (CLARIFY: Can it be a deferred procedure call at interrupt context? Would be different requirement)
<<<

[REQUIREMENT]
UID: ZEP-61
STATUS: Draft
TYPE: Functional
COMPONENT: Interrupts
TITLE: Enabling interrupts
STATEMENT: >>>
The Zephyr RTOS shall provide mechanisms to enable interrupts.
<<<
USER_STORY: >>>
As a Zephyr RTOS user I want to be able to enable each individual and a global interrupt according to my applications needs during program execution.
<<<

[REQUIREMENT]
UID: ZEP-62
STATUS: Draft
TYPE: Functional
COMPONENT: Interrupts
TITLE: Disabling interrupts
STATEMENT: >>>
The Zephyr RTOS shall provide mechanisms to disable interrupts.
<<<
USER_STORY: >>>
As a Zephyr RTOS user I want to be able to disable each individual and a global interrupt according to my applications needs during program execution.
<<<

[/SECTION]

[SECTION]
TITLE: Logging

[REQUIREMENT]
UID: ZEP-63
STATUS: Draft
TYPE: Functional
COMPONENT: Logging
TITLE: Dedicated Logging Thread Support
STATEMENT: >>>
The Zephyr RTOS shall support isolation of logging from other functionality.
<<<
USER_STORY: >>>
As a Zephyr RTOS user I want to be able to configure logging of events so the execution of logging activities does have no or only a minimal impact to the timing behaviour of my application.
<<<

[REQUIREMENT]
UID: ZEP-64
STATUS: Draft
TYPE: Functional
COMPONENT: Logging
TITLE: Logs available for post processing
STATEMENT: >>>
The Zephyr RTOS logging shall produce logs that are capable of being post processed.
<<<
USER_STORY: >>>
As a Zephyr RTOS user I want the logging information to be stored in a format which allows to be read possibly converted or displayed by COTS tools.
<<<

[REQUIREMENT]
UID: ZEP-65
STATUS: Draft
TYPE: Functional
COMPONENT: Logging
TITLE: Formatting log messages
STATEMENT: >>>
The Zephyr RTOS logging shall support formatting of log messages to enable filtering.
<<<
USER_STORY: >>>
As a Zephyr RTOS user I want to be able my application to format texts (printf alike) into the log message.
<<<
REVIEW_COMMENT: >>>
Question: formatting in which way? length, colour, tags, etc?
<<<

[REQUIREMENT]
UID: ZEP-66
STATUS: Draft
TYPE: Functional
COMPONENT: Logging
TITLE: Logging Filtering Support
STATEMENT: >>>
The Zephyr RTOS logging system shall support filtering based on severity level.
<<<
USER_STORY: >>>
As a Zephyr RTOS user I want to be able to distinguish between different severity level for my log messages (e.g. DEBUG, INFO, WARN, ERROR, PANIC).
<<<
REVIEW_COMMENT: >>>
Question: Filtering during runtime or a kconfig option to initially set the filter for logging
<<<

[REQUIREMENT]
UID: ZEP-67
STATUS: Draft
TYPE: Functional
COMPONENT: Logging
TITLE: Multiple Backend Logging Support
STATEMENT: >>>
The Zephyr RTOS shall support logging messages to multiple system resources.
<<<
USER_STORY: >>>
As a Zephyr RTOS user I want to be able to simultaneously log to different channels which may store / redirect the information on / to different hardware (EEPROM, Flash, FRAM, UART, Ethernet, USB etc.).
<<<
REVIEW_COMMENT: >>>
Question: What kind of backends shall be supported? More than one at a time?   Word choices.... backends/devices/channels/destinations/resources (devices, memory, ....) )
<<<

[REQUIREMENT]
UID: ZEP-68
STATUS: Draft
TYPE: Functional
COMPONENT: Logging
TITLE: Deferred Logging Support
STATEMENT: >>>
The Zephyr RTOS shall support deferred logging (TODO: need more detail about the constraints and limits on what can be deferred).
<<<
USER_STORY: >>>
As a Zephyr RTOS user I want a minimal influence of logging activities to the timing behaviour of my application. Time consuming logging threads shall be done in the background.
<<<

[/SECTION]

[SECTION]
TITLE: Memory protection

[REQUIREMENT]
UID: ZEP-69
STATUS: Draft
TYPE: Functional
COMPONENT: Memory Protection
TITLE: Memory Protection
STATEMENT: >>>
The Zephyr RTOS shall support memory protection features to isolate a thread's memory region.
<<<
USER_STORY: >>>
As a Zephyr RTOS user I want memory to be allocated and protected to my application threads preventing mistakenly access to foreign memory as far as the hardware allows.
<<<
REVIEW_COMMENT: >>>
Functional it is memory management, but it also strongly relates to the architecture abstraction and memory access
<<<

[REQUIREMENT]
UID: ZEP-70
STATUS: Draft
TYPE: Functional
COMPONENT: Memory Protection
TITLE: Granting access to kernel objects
STATEMENT: >>>
The Zephyr RTOS shall provide a mechanism to grant user threads access to kernel objects.
<<<
USER_STORY: >>>
As a Zephyr RTOS user I want, from the user space, under certain conditions, access to kernel objects.
<<<
REVIEW_COMMENT: >>>
What are the conditions to a user thread to get access to a kernel object?
<<<

[REQUIREMENT]
UID: ZEP-71
STATUS: Draft
TYPE: Functional
COMPONENT: Memory Protection
TITLE: Separation between user and kernel threads for memory access
STATEMENT: >>>
The Zephyr RTOS shall be able to differentiate between user threads and kernel threads for memory access.
<<<
USER_STORY: >>>
As a Zephyr RTOS user I want, from the kernel space, unconditioned access to kernel objects.
<<<

[REQUIREMENT]
UID: ZEP-72
STATUS: Draft
TYPE: Functional
COMPONENT: Memory Protection
TITLE: Safely handle unimplemented calls or invalid system calls
STATEMENT: >>>
The Zephyr RTOS shall have a defined behaviour when an invocation of an unimplemented system call is made.
<<<
USER_STORY: >>>
As a Zephyr RTOS user I want Zephyr OS to indicate any unimplemented system call by an appropriate error message.
<<<
REVIEW_COMMENT: >>>
What is an "unimplemented system call"? An empty system call function? Can I call something that is not there it all? Isn't this more a topic for security? - makes sense to handle this from the safety perspective, but still raises some questions here.
<<<

[REQUIREMENT]
UID: ZEP-73
STATUS: Draft
TYPE: Functional
COMPONENT: Memory Protection
TITLE: Response to invalid system call IDs
STATEMENT: >>>
The Zephyr RTOS shall have a defined behaviour when an invalid system call ID is used.
<<<
USER_STORY: >>>
As a Zephyr RTOS user I want Zephyr OS to indicate invalid system call by an appropriate error message.
<<<

[REQUIREMENT]
UID: ZEP-74
STATUS: Draft
TYPE: Functional
COMPONENT: Memory Protection
TITLE: Prevent user threads creating higher priority threads
STATEMENT: >>>
The Zephyr RTOS shall prevent user threads from creating new threads that are higher priority than the caller.
<<<

[REQUIREMENT]
UID: ZEP-75
STATUS: Draft
TYPE: Functional
COMPONENT: Memory Protection
TITLE: Revoking threads permissions on a kernel object
STATEMENT: >>>
The Zephyr RTOS shall support revoking permission to a kernel object. User mode threads may only revoke their own access to an object.
<<<
USER_STORY: >>>
As a Zephyr RTOS user I want to be protected against other user threads changing access to kernel objects of my thread.
<<<

[REQUIREMENT]
UID: ZEP-76
STATUS: Draft
TYPE: Functional
COMPONENT: TBD: Memory Protection --> Thread
TITLE: Prevent user threads creating supervisor threads
STATEMENT: >>>
The Zephyr RTOS shall prevent user threads from creating kernel threads.
<<<
USER_STORY: >>>
As a Zephyr RTOS user I want to be protected against user threads creating higher privileged kernel/supervisor threads.
<<<

[REQUIREMENT]
UID: ZEP-77
STATUS: Draft
TYPE: Functional
COMPONENT: TBD: Memory Protection --> Thread
TITLE: Reduced Privilege Level Threads
STATEMENT: >>>
The Zephyr RTOS shall allow the creation of threads that run in reduced privilege level.
<<<
USER_STORY: >>>
As a Zephyr RTOS user I want to be able to create lower privileged threads than my own.
<<<

[REQUIREMENT]
UID: ZEP-78
STATUS: Draft
TYPE: Functional
COMPONENT: Memory Protection
TITLE: User Mode Threads Performing Privileged Operations
STATEMENT: >>>
The Zephyr RTOS shall provide system calls to allow user mode threads to perform privileged operations.
<<<
USER_STORY: >>>
As a Zephyr RTOS user I want to be able to perform privileged operations in the kernel mode through a well defined interface.
<<<

[REQUIREMENT]
UID: ZEP-79
STATUS: Draft
TYPE: Functional
COMPONENT: Memory Protection
TITLE: User mode handling of detected stack overflow
STATEMENT: >>>
The Zephyr RTOS shall support a defined mechanism for user mode handling a of detected stack overflow.
<<<
USER_STORY: >>>
As a Zephyr RTOS user I want, when a stack overflow is detected, to be able to implement a graceful, application defined handling of the exception.
<<<
REVIEW_COMMENT: >>>
Need for handlers and callbacks outside of thread.   Need to be able to answer "Can the safety application rely on Zephyr to reach the safe state after stack overflow occurred?"   Can it handle degraded mode.
<<<

[REQUIREMENT]
UID: ZEP-80
STATUS: Draft
TYPE: Functional
COMPONENT: Memory Protection
TITLE: Stack Overflow Detection
STATEMENT: >>>
The Zephyr RTOS shall support detection of stack overflows.
<<<
USER_STORY: >>>
As a Zephyr RTOS user I want to get an indication when a stack overflow occurs at least during debugging / the development phase, and for safety applications also in a release version of my application.
<<<
REVIEW_COMMENT: >>>
RS: IMHO should be configurable due the to performance penalty introduced with it.   - DL:  THere are various modes,  canaries, and they can be turned off.  KS:  Clearly safety & security mechanism.
<<<

[REQUIREMENT]
UID: ZEP-81
STATUS: Draft
TYPE: Functional
COMPONENT: Memory Protection
TITLE: Boot Time Memory Access Policy
STATEMENT: >>>
The Zephyr RTOS shall support configurable access to memory during boot time.
<<<
REVIEW_COMMENT: >>>
What does "policy" mean in this context? Does this mean to choose between different start up sequences?
<<<

[REQUIREMENT]
UID: ZEP-82
STATUS: Draft
TYPE: Functional
COMPONENT: Memory Protection
TITLE: System Call Handler Functions
STATEMENT: >>>
The Zephyr RTOS shall provide helper functions for system call handler functions to validate the inputs passed in from user mode before invoking the implementation function to protect the kernel.
<<<
USER_STORY: >>>
As a Zephyr RTOS user I want Zepyhr OS to validate system call parameters passed from the user mode to the kernel mode to avoid crashes and undefined behaviour.
<<<
REVIEW_COMMENT: >>>
I do not understand that. What kind of helper functions? Kind of plausibility checks? Does it make sense to provide this functionality on OS level?   David:  These are likely just validation that the parameters are not going to be dangerous (security/safety).
<<<

[REQUIREMENT]
UID: ZEP-83
STATUS: Draft
TYPE: Functional
COMPONENT: Memory Protection
TITLE: System Call C strings in user mode
STATEMENT: >>>
The Zephyr RTOS shall support system calls to be able to safely accept C strings passed in from user mode.
<<<
USER_STORY: >>>
As a Zephyr RTOS user I want Zepyhr OS to validate system call string type parameters passed from the user mode to the kernel mode to avoid crashes and undefined behaviour.

e.g.

- verify the string length is smaller or equal to the syscalls defined max.
- verify that the length type does not overflow when allocating one more byte ???
<<<
REVIEW_COMMENT: >>>
Is this a helper function like mentioned in ZEP133? What does C string mean here? Like a string variable that's passed down from user mode to ??? by a system call?
<<<

[REQUIREMENT]
UID: ZEP-84
STATUS: Draft
TYPE: Functional
COMPONENT: Memory Protection
TITLE: Tracking kernel objects in used by user mode threads
STATEMENT: >>>
The Zephyr RTOS shall track kernel objects that are used by user mode threads.

Note: this means Zephyr shall track the resources used by the user mode thread (associate this with a user story).
<<<
REVIEW_COMMENT: >>>
Does this mean that the user mode threads are monitored wrt to their usage of kernel objects?  Example/User story would help.
<<<

[REQUIREMENT]
UID: ZEP-85
STATUS: Draft
TYPE: Functional
COMPONENT: Memory Protection
TITLE: Granting threads access to specific memory
STATEMENT: >>>
The Zephyr RTOS shall have an interface to request access to specific memory after initial allocation.
<<<
USER_STORY: >>>
As a Zephyr RTOS user I want to be able to request read-only or read-write access to a dedicated memory area/pool during runtime.
<<<

[REQUIREMENT]
UID: ZEP-86
STATUS: Draft
TYPE: Functional
COMPONENT: Memory Protection
TITLE: Assigning memory pools to act as a thread resource pool
STATEMENT: >>>
The Zephyr RTOS shall support assigning a memory pool to act as that thread's resource pool.
<<<
USER_STORY: >>>
As a Zephyr RTOS user I want to be able, during runtime from the kernel, to request a memory area/pool which is exclusively available to the requesting thread protected against access from other threads.
<<<
REVIEW_COMMENT: >>>
What is the difference to ZEP 136? Read & Write, while ZEP136 is just read?
<<<

[/SECTION]

[SECTION]
TITLE: Memory Objects

[REQUIREMENT]
UID: ZEP-87
STATUS: Draft
TYPE: Functional
COMPONENT: Memory Objects
TITLE: Dynamic Memory Allocation
STATEMENT: >>>
The Zephyr RTOS shall allow threads to dynamically allocate variable-sized memory regions from a specified range of memory.
<<<
USER_STORY: >>>
As a Zephyr RTOS user I want my application to be able to dynamically allocate memory of a application defined size.
<<<
REVIEW_COMMENT: >>>
Is dynamic memory allocation only allowed in memory pool objects?
<<<

[REQUIREMENT]
UID: ZEP-88
STATUS: Draft
TYPE: Functional
COMPONENT: Memory Objects
TITLE: Memory Slab Object
STATEMENT: >>>
The Zephyr RTOS shall allow threads to dynamically allocate fixed-sized memory regions from a specified range of memory.
<<<
USER_STORY: >>>
As a Zephyr RTOS user I want a most efficient and least fragmentation prone dynamic memory allocation mechanism.
<<<

[/SECTION]

[SECTION]
TITLE: Data Passing

[REQUIREMENT]
UID: ZEP-89
STATUS: Draft
TYPE: Functional
COMPONENT: Data Passing
TITLE: Traditional FIFO Queue
STATEMENT: >>>
The Zephyr RTOS shall provide a kernel object that implements a traditional first in, first out (FIFO) queue, allowing threads and ISRs to add and remove a limited number of 32-bit data values.
<<<
USER_STORY: >>>
As a Zephyr RTOS user I want to be able to exchange 1 to N data objects between different threads and ISR in a thread-safe manner with a first-in-first-out (queue) behaviour.
<<<

[REQUIREMENT]
UID: ZEP-90
STATUS: Draft
TYPE: Functional
COMPONENT: Data Passing
TITLE: Traditional LIFO queue
STATEMENT: >>>
The Zephyr RTOS shall provide a kernel object that implements a traditional last in, first out (LIFO) queue, allowing threads and ISRs to add and remove a limited number of 32-bit data values.
<<<
USER_STORY: >>>
As a Zephyr RTOS user I want to be able to exchange 1 to N data objects between different threads and ISR in a thread-safe manner with a last-in-first-out (stack) behaviour.
<<<

[/SECTION]

[SECTION]
TITLE: Mutex

[REQUIREMENT]
UID: ZEP-91
STATUS: Draft
TYPE: Functional
COMPONENT: Mutex
TITLE: Mutex Kernel Object
STATEMENT: >>>
The Zephyr RTOS shall support resource synchronization. (Note synchronization can be for memory access, and mutex may be one implementation, but not the only one).
<<<
USER_STORY: >>>
As a Zephyr RTOS user I want to be able to sychonize threads when accessing common resources, where the thread shall have the option to:
- wait eternally until the resources becomes available.
- immediately return with a negative message if the resource is not available and allow the thread to continue.
- wait for a given time for the resource to become available or return with a negative message.
<<<
REVIEW_COMMENT: >>>
Concern over phrase recursive.  What is it MUTEXing? Memory Management?
<<<

[/SECTION]

[SECTION]
TITLE: Power Management

[REQUIREMENT]
UID: ZEP-92
STATUS: Draft
TYPE: Functional
COMPONENT: Power Management
TITLE: Power State Control
STATEMENT: >>>
The Zephyr RTOS shall provide control over changes to system power states.
<<<
USER_STORY: >>>
See ZEP104
+
When the power state is changed I want to get an notification in order for specific parts of my application to react accordingly.
<<<

[REQUIREMENT]
UID: ZEP-93
STATUS: Draft
TYPE: Functional
COMPONENT: Power Management
TITLE: Power Management - TBD
STATEMENT: >>>
TBD
<<<

[REQUIREMENT]
UID: ZEP-94
STATUS: Draft
TYPE: Functional
COMPONENT: Power Management
TITLE: Notification of changes to system power states
STATEMENT: >>>
The Zephyr RTOS shall provide notification of changes to system power states.
<<<

[/SECTION]

[SECTION]
TITLE: Thread Communication

[REQUIREMENT]
UID: ZEP-96
STATUS: Draft
TYPE: Functional
COMPONENT: Thread Communication
TITLE: Exchanging data between threads
STATEMENT: >>>
The Zephyr RTOS shall provide a mechanism for exchanging data between threads.
<<<
USER_STORY: >>>
(Note: copying data may be needed here - what is Zephyr doing? is it configurable?)
<<<

[REQUIREMENT]
UID: ZEP-97
STATUS: Draft
TYPE: Functional
COMPONENT: Thread Communication
TITLE: Waiting for results during communication
STATEMENT: >>>
The Zephyr RTOS shall provide mechanisms to enable waiting for results during communication between threads. (NOTE:  waiting for results is really bad and dangerous, want to avoid if at all possible).
<<<
USER_STORY: >>>
=N73
<<<

[REQUIREMENT]
UID: ZEP-100
STATUS: Draft
TYPE: Functional
COMPONENT: Thread Communication
TITLE: Poll Operation Support
STATEMENT: >>>
The Zephyr RTOS shall support a poll operation which enables waiting concurrently for any one of multiple conditions to be fulfilled.
<<<
USER_STORY: >>>
As a Zephyr RTOS user I want my thread to wait for one of several defined events to occur and only continue when one of them has occurred.
<<<

[REQUIREMENT]
UID: ZEP-101
STATUS: Draft
TYPE: Functional
COMPONENT: Thread Communication
TITLE: Pipe Communication Primitive
STATEMENT: >>>
The Zephyr RTOS shall provide a communication primitive that allows a thread to transfer a block of
data to another thread.
<<<
USER_STORY: >>>
As a Zephyr RTOS user I want to send a byte stream from one thread to another in a thread-safe manner.
<<<

[REQUIREMENT]
UID: ZEP-102
STATUS: Draft
TYPE: Functional
COMPONENT: Thread Communication
TITLE: Message Queue
STATEMENT: >>>
The Zephyr RTOS shall provide a a communication primitive that allow threads and ISRs to asynchronously exchange fixed-size data items.
<<<

[REQUIREMENT]
UID: ZEP-103
STATUS: Draft
TYPE: Functional
COMPONENT: Thread Communication
TITLE: Mailbox Kernel Primitive
STATEMENT: >>>
The Zephyr RTOS shall provide a communication primitive that allows threads to exchange messages of varying sizes asynchronously or synchronously.
<<<
USER_STORY: >>>
As a Zephyr RTOS user I want a sending thread to deposit a message into the mailbox,
and a receiving thread to be able to retrieve the message at its convenience. This
allows for asynchronous communication, where threads do not need to synchronize their
execution explicitly.
<<<

[SECTION]
TITLE: Counting Semaphore

[SECTION]
TITLE: Initialization

[REQUIREMENT]
UID: ZEP-134
STATUS: Draft
TYPE: Functional
COMPONENT: Counting Semaphore
TITLE: Build-Time Allocation and Initialization
STATEMENT: >>>
The Zephyr RTOS shall expose an interface for a Counting Semaphore to accomplish all of the following at build-time:

- statically allocating the Counting Semaphore;
- statically initialize the Counting Semaphore with the provided count limit and initial count.
<<<

[REQUIREMENT]
UID: ZEP-135
STATUS: Draft
TYPE: Functional
COMPONENT: Counting Semaphore
TITLE: Dynamic Initialization
STATEMENT: >>>
The Zephyr RTOS shall expose an interface to dynamically initialize a Counting Semaphore which requires the following information:

- initial count of the Counting Semaphore;
- count limit of the Counting Semaphore.
<<<

[/SECTION]

[SECTION]
TITLE: Semaphore Give

[REQUIREMENT]
UID: ZEP-128
STATUS: Draft
TYPE: Functional
COMPONENT: Counting Semaphore
TITLE: Semaphore Give without Waiting Threads
STATEMENT: >>>
While no thread is waiting for a Counting Semaphore,

When a thread gives that Counting Semaphore,

the Zephyr RTOS shall accomplish all of the following:

- increase the Semaphore Count by 1;
- indicate SUCCESS to the giving thread.
<<<

[REQUIREMENT]
UID: ZEP-127
STATUS: Draft
TYPE: Functional
COMPONENT: Counting Semaphore
TITLE: Semaphore Give while Thread Waiting
STATEMENT: >>>
While a thread is waiting for a Counting Semaphore,

When a thread gives that Counting Semaphore,

the Zephyr RTOS shall accomplish all of the following:

- unblock the highest priority thread waiting for that Counting Semaphore;
- indicate SUCCESS to the giving thread.
<<<

[/SECTION]

[SECTION]
TITLE: Semaphore Take

[REQUIREMENT]
UID: ZEP-129
STATUS: Draft
TYPE: Functional
COMPONENT: Counting Semaphore
TITLE: Semaphore Take while Available
STATEMENT: >>>
While a Counting Semaphore count is > 0,

When a takes that Counting Semaphore,

the Zephyr RTOS shall accomplish all of the following:

- decrement by 1 the count of that Counting Semaphore;
- indicate SUCCESS to the taking thread.
<<<

[REQUIREMENT]
UID: ZEP-131
STATUS: Draft
TYPE: Functional
COMPONENT: Counting Semaphore
TITLE: Semaphore Take w/o blocking when not Available
STATEMENT: >>>
While a Counting Semaphore count is 0,

When a thread takes that Counting Semaphore without allowing blocking,

the Zephyr RTOS shall indicate NOT AVAILABLE to the taking thread.
<<<

[REQUIREMENT]
UID: ZEP-130
STATUS: Draft
TYPE: Functional
COMPONENT: Counting Semaphore
TITLE: Semaphore Take with TIMEOUT > 0 blocks if not Available
STATEMENT: >>>
While a Counting Semaphore count is 0,

When a thread takes that Counting Semaphore with a waiting TIMEOUT > 0,

the Zephyr RTOS shall accomplish all of the following:

- block the taking thread waiting for the availability of that Counting Semaphore;
- enter the waiting period with a duration TIMEOUT.
<<<

[REQUIREMENT]
UID: ZEP-132
STATUS: Draft
TYPE: Functional
COMPONENT: Counting Semaphore
TITLE: Semaphore Take Unblocked by Giving Thread
STATEMENT: >>>
When the waiting thread is unblocked by a giving thread,

the Zephyr RTOS shall accomplish all of the following:

- deactivate the waiting period;
- indicate SUCCESS to the waiting thread;
- reschedule the waiting thread.
<<<

[REQUIREMENT]
UID: ZEP-133
STATUS: Draft
TYPE: Functional
COMPONENT: Counting Semaphore
TITLE: Semaphore Take Unblocked by Waiting Period Timeout
STATEMENT: >>>
When the waiting thread is unblocked by the expiration of the waiting period,

the Zephyr RTOS shall accomplish all of the following:

- resume the waiting thread;
- indicate TIMEDOUT to the waiting thread;
- reschedule the waiting thread.
<<<

[/SECTION]

[SECTION]
TITLE: Semaphore Count

[REQUIREMENT]
UID: ZEP-136
STATUS: Draft
TYPE: Functional
COMPONENT: Counting Semaphore
TITLE: Current Count
STATEMENT: >>>
When the Counting Semaphore current count is requested,

the Zephyr RTOS shall report the current count of the Counting Semaphore.
<<<

[/SECTION]

[/SECTION]

[/SECTION]

[SECTION]
TITLE: Thread Scheduling

[REQUIREMENT]
UID: ZEP-104
STATUS: Draft
TYPE: Functional
COMPONENT: Multi Core
TITLE: Support operation on more than one CPU
STATEMENT: >>>
The Zephyr RTOS shall support operation on more than one physical CPU sharing the same kernel state.
<<<

[REQUIREMENT]
UID: ZEP-105
STATUS: Draft
TYPE: Functional
COMPONENT: Multi Core
TITLE: Running threads on specific CPUs
STATEMENT: >>>
The Zephyr RTOS shall provide an interface for running threads on specific sets of CPUs ( default is 1 CPU).
<<<
USER_STORY: >>>
As a Zephyr RTOS user I want Zephyr OS to be able to specify the CPU core or the set of CPU cores on which a thread shall be executed.
<<<

[REQUIREMENT]
UID: ZEP-106
STATUS: Draft
TYPE: Functional
COMPONENT: Multi Core
TITLE: Exclusion between physical CPUs
STATEMENT: >>>
The Zephyr RTOS shall provide an interface for mutual exclusion between multiple physical CPUs.
<<<
USER_STORY: >>>
As a Zephyr RTOS user I want Zephyr OS to provide synchronization mechanisms between the CPU cores and the access to common resources.
<<<

[/SECTION]

[SECTION]
TITLE: Thread Scheduling

[REQUIREMENT]
UID: ZEP-112
STATUS: Draft
TYPE: Functional
COMPONENT: Thread Scheduling
TITLE: Scheduling a thread based on an event
STATEMENT: >>>
The Zephyr RTOS shall provide an interface to schedule a thread based on an event.
<<<
USER_STORY: >>>
As a Zephyr RTOS user, I want to be able to execute work which reacts on events and interrupts the current executed work.
<<<
RELATIONS:
- TYPE: Parent
  VALUE: ZEP-123

[REQUIREMENT]
UID: ZEP-114
STATUS: Draft
TYPE: Functional
COMPONENT: Thread Scheduling
TITLE: Deadline Scheduling Priorities
STATEMENT: >>>
The Zephyr RTOS shall organize running threads by earliest deadline first priority.
<<<
USER_STORY: >>>
As a Zephyr RTOS user, I want to be able to schedule threads by earliest deadline first.
<<<

[REQUIREMENT]
UID: ZEP-115
STATUS: Draft
TYPE: Functional
COMPONENT: Thread Scheduling
TITLE: Work Queue utility capable of running preemptible work items
STATEMENT: >>>
The Zephyr RTOS shall provide a thread-pooled work queue utility capable of running preemptible work items with specific scheduler priorities.
<<<
USER_STORY: >>>
As a Zephyr RTOS user, I want to be able to add work items in a thread work queue with different priorities and these shall be scheduled according their priorities.
<<<

[REQUIREMENT]
UID: ZEP-24
STATUS: Draft
TYPE: Functional
COMPONENT: Thread Scheduling
TITLE: Run user supplied functions in-order in a separate thread(s)
STATEMENT: >>>
The Zephyr RTOS shall provide an interface for running user-supplied functions.
<<<
USER_STORY: >>>
As a Zephyr RTOS user, I want to be able to run functions in-order in a separated thread/threads.
<<<
REVIEW_COMMENT: >>>
Where do we put this,  thread, scheduling or???
<<<

[REQUIREMENT]
UID: ZEP-116
STATUS: Draft
TYPE: Functional
COMPONENT: Thread Scheduling
TITLE: Organize running threads into a fixed list
STATEMENT: >>>
The Zephyr RTOS shall organize running threads into a fixed list of numeric priorities.
<<<
USER_STORY: >>>
As a Zephyr RTOS user, I want that the OS organize running threads in a fixed list of numeric priorities.
<<<
REVIEW_COMMENT: >>>
The Zephyr RTOS shall allow prioritizing threads
<<<

[REQUIREMENT]
UID: ZEP-117
STATUS: Draft
TYPE: Functional
COMPONENT: Thread Scheduling
TITLE: Preemption support
STATEMENT: >>>
The Zephyr RTOS shall support preemption of a running thread by a higher priority thread.
<<<
USER_STORY: >>>
As a Zephyr RTOS user, I want that the OS preempt running threads by a thread with higher priority.
<<<

[REQUIREMENT]
UID: ZEP-118
STATUS: Draft
TYPE: Functional
COMPONENT: Thread Scheduling
TITLE: Un-preemptible thread priorities
STATEMENT: >>>
The Zephyr RTOS shall support thread priorities which cannot be preempted by other user threads.
<<<
USER_STORY: >>>
As a Zephyr RTOS user, I want to be able to configure thread prioritizes which cannot be preempted by other user threads.
<<<

[REQUIREMENT]
UID: ZEP-119
STATUS: Draft
TYPE: Functional
COMPONENT: Thread Scheduling
TITLE: Time sharing of CPU resources
STATEMENT: >>>
The Zephyr RTOS shall support time sharing of CPU resources among threads of the same priority.
<<<
USER_STORY: >>>
As a Zephyr RTOS user, I want to be able to configure my RTOS in the way, that the CPU resources are shared evenly among executed threads of the same priority.
<<<
REVIEW_COMMENT: >>>
what does traditional mean here?   Round robin?
<<<

[/SECTION]

[SECTION]
TITLE: Threads

[REQUIREMENT]
UID: ZEP-23
STATUS: Draft
TYPE: Functional
COMPONENT: Threads
TITLE: Creating threads
STATEMENT: >>>
The Zephyr RTOS shall provide an interface to create (start) a thread.
<<<
RELATIONS:
- TYPE: Parent
  VALUE: ZEP-123
- TYPE: Parent
  VALUE: ZEP-5

[REQUIREMENT]
UID: ZEP-107
STATUS: Draft
TYPE: Functional
COMPONENT: Threads
TITLE: Setting thread priority
STATEMENT: >>>
The Zephyr RTOS shall provide an interface to set a thread's priority.
<<<
RELATIONS:
- TYPE: Parent
  VALUE: ZEP-122

[REQUIREMENT]
UID: ZEP-108
STATUS: Draft
TYPE: Functional
COMPONENT: Threads
TITLE: Suspending a thread
STATEMENT: >>>
The Zephyr RTOS shall provide an interface to suspend a thread.
<<<
RELATIONS:
- TYPE: Parent
  VALUE: ZEP-123
- TYPE: Parent
  VALUE: ZEP-5

[REQUIREMENT]
UID: ZEP-109
STATUS: Draft
TYPE: Functional
COMPONENT: Threads
TITLE: Resuming a suspended thread
STATEMENT: >>>
The Zephyr RTOS shall provide an interface to resume a suspended thread.
<<<
RELATIONS:
- TYPE: Parent
  VALUE: ZEP-123
- TYPE: Parent
  VALUE: ZEP-5

[REQUIREMENT]
UID: ZEP-110
STATUS: Draft
TYPE: Functional
COMPONENT: Threads
TITLE: Resuming a suspended thread after a timeout
STATEMENT: >>>
The Zephyr RTOS shall provide an interface to resume a suspended thread after a timeout.
<<<
RELATIONS:
- TYPE: Parent
  VALUE: ZEP-123
- TYPE: Parent
  VALUE: ZEP-5

[REQUIREMENT]
UID: ZEP-111
STATUS: Draft
TYPE: Functional
COMPONENT: Threads
TITLE: Deleting a thread
STATEMENT: >>>
The Zephyr RTOS shall provide an interface to delete (end) a thread.
<<<
RELATIONS:
- TYPE: Parent
  VALUE: ZEP-123
- TYPE: Parent
  VALUE: ZEP-5

[REQUIREMENT]
UID: ZEP-124
STATUS: Draft
TYPE: Functional
COMPONENT: Threads
TITLE: Thread states
STATEMENT: >>>
Threads shall have different states to fulfill the Life-cycle of a thread
<<<
USER_STORY: >>>
As a Zephyr RTOS user, I want to know in what state a specific thread is.
<<<
RELATIONS:
- TYPE: Parent
  VALUE: ZEP-123
- TYPE: Parent
  VALUE: ZEP-5

[REQUIREMENT]
UID: ZEP-98
STATUS: Draft
TYPE: Functional
COMPONENT: Threads
TITLE: Thread stack objects
STATEMENT: >>>
Every Thread shall have it's own stack.
<<<
USER_STORY: >>>
As a Zephyr RTOS user I want to be able to configure the stack size of a thread. And every thread shall have it's own dedicated stack.
<<<
RELATIONS:
- TYPE: Parent
  VALUE: ZEP-123
- TYPE: Parent
  VALUE: ZEP-5

[REQUIREMENT]
UID: ZEP-25
STATUS: Draft
TYPE: Functional
COMPONENT: Threads
TITLE: Thread privileges
STATEMENT: >>>
The Zephyr RTOS shall provide an interface to create threads with defined privilege.
<<<
RELATIONS:
- TYPE: Parent
  VALUE: ZEP-123
- TYPE: Parent
  VALUE: ZEP-5

[REQUIREMENT]
UID: ZEP-26
STATUS: Draft
TYPE: Functional
COMPONENT: Threads
TITLE: Scheduling multiple threads
STATEMENT: >>>
The Zephyr RTOS shall provide an interface to schedule multiple threads.
<<<
RELATIONS:
- TYPE: Parent
  VALUE: ZEP-5

[REQUIREMENT]
UID: ZEP-125
STATUS: Draft
TYPE: Functional
COMPONENT: Threads
TITLE: Thread Options
STATEMENT: >>>
The Zephyr RTOS shall support a set of thread options.
<<<
USER_STORY: >>>
As a Zephyr RTOS user, I want to be able to pass specific option to a thread.
<<<
RELATIONS:
- TYPE: Parent
  VALUE: ZEP-123
- TYPE: Parent
  VALUE: ZEP-5

[REQUIREMENT]
UID: ZEP-126
STATUS: Draft
TYPE: Functional
COMPONENT: Threads
TITLE: Thread Custom Data
STATEMENT: >>>
Every thread shall have a custom data area.
<<<
USER_STORY: >>>
As a Zephyr RTOS user, I want to be able to set a thread specific custom area for every thread I create and which can be used only by the thread itself or the can be used by the application
<<<
RELATIONS:
- TYPE: Parent
  VALUE: ZEP-123
- TYPE: Parent
  VALUE: ZEP-5

[/SECTION]

[SECTION]
TITLE: Timers

[REQUIREMENT]
UID: ZEP-27
STATUS: Draft
TYPE: Functional
COMPONENT: Timers
TITLE: Kernel Clock
STATEMENT: >>>
The Zephyr RTOS shall provide a interface for checking the current value of the real-time clock.
<<<
USER_STORY: >>>
As a Zephyr RTOS user, I want to be able to track the passed real time in the OS with a dedicated hardware counter and interrupt.
<<<
RELATIONS:
- TYPE: Parent
  VALUE: ZEP-6

[REQUIREMENT]
UID: ZEP-28
STATUS: Draft
TYPE: Functional
COMPONENT: Timers
TITLE: Call functions in interrupt context
STATEMENT: >>>
The Zephyr RTOS shall provide an interface to schedule user mode call back function triggered by a real time clock value.
<<<
USER_STORY: >>>
As a Zephyr RTOS user, I want to be able to execute functions in the interrupt context and the interrupt context shall be base on a real-time counter.
<<<
RELATIONS:
- TYPE: Parent
  VALUE: ZEP-6

[/SECTION]

[SECTION]
TITLE: Tracing

[REQUIREMENT]
UID: ZEP-29
STATUS: Draft
TYPE: Functional
COMPONENT: Tracing
TITLE: Initializing a trace
STATEMENT: >>>
The Zephyr RTOS shall provide an interface to initialize a trace.
<<<

[REQUIREMENT]
UID: ZEP-30
STATUS: Draft
TYPE: Functional
COMPONENT: Tracing
TITLE: Triggering a trace
STATEMENT: >>>
The Zephyr RTOS shall provide an interface to trigger a trace.
<<<

[REQUIREMENT]
UID: ZEP-31
STATUS: Draft
TYPE: Functional
COMPONENT: Tracing
TITLE: Dumping trace results
STATEMENT: >>>
The Zephyr RTOS shall provide an interface to dump results from a trace.
<<<

[REQUIREMENT]
UID: ZEP-32
STATUS: Draft
TYPE: Functional
COMPONENT: Tracing
TITLE: Removing trace data
STATEMENT: >>>
The Zephyr RTOS shall provide an interface to remove trace data.
<<<

[REQUIREMENT]
UID: ZEP-33
STATUS: Draft
TYPE: Functional
COMPONENT: Tracing
TITLE: Tracing Object  Identification
STATEMENT: >>>
The Zephyr RTOS shall provide an interface to identify the objects being traced.
<<<
USER_STORY: >>>
As a Zepyhr OS user, I want to be able to give each object which I create a name / label in order to be able to identify them in a trace log.
<<<
REVIEW_COMMENT: >>>
What objects?   hardware devices, code, ....
<<<

[REQUIREMENT]
UID: ZEP-34
STATUS: Draft
TYPE: Functional
COMPONENT: Tracing
TITLE: Tracing Non-Interference
STATEMENT: >>>
Zepyhr shall prevent the tracing functionality from interfering with normal operations.
<<<
USER_STORY: >>>
As a Zepyhr OS user, I want that the trace functionality do not interfere or slow down the operation system functionality.
<<<
REVIEW_COMMENT: >>>
What are "normal" operations? Might make sense to rephrase this to "any other operation"
<<<

[/SECTION]
