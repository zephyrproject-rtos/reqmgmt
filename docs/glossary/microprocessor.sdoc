[DOCUMENT]
TITLE: microprocessor

[FREETEXT]
microprocessor.

(1) processor whose elements have been miniaturized into one or a few integrated circuits (ISO/IEC 2382:2015 Information technology -- Vocabulary)
[/FREETEXT]
