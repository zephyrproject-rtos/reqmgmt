[DOCUMENT]
TITLE: bootstrap

[FREETEXT]
bootstrap.

(1) short computer program that is permanently resident or easily loaded into a computer and whose execution brings a larger program, such as an operating system or its loader, into memory (ISO/IEC/IEEE 24765:2017 Systems and software engineering-Vocabulary)

(2) to use a program to bring up a larger program, such as an operating system (ISO/IEC/IEEE 24765:2017 Systems and software engineering-Vocabulary)

Example: null
[/FREETEXT]
