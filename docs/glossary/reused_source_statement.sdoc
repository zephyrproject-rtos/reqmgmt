[DOCUMENT]
TITLE: reused source statement

[FREETEXT]
reused source statement.

(1) unmodified source statement obtained for the product from an external source (ISO/IEC/IEEE 24765:2017 Systems and software engineering-Vocabulary)
[/FREETEXT]
