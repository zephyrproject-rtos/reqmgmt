[DOCUMENT]
TITLE: central processing unit (CPU)

[FREETEXT]
CPU.

(1) central processing unit (IEEE 1012-2016 IEEE Standard for System, Software, and Hardware Verification and Validation, 3.1)
[/FREETEXT]
