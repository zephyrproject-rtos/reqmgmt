[DOCUMENT]
TITLE: reuse

[FREETEXT]
reuse.

(1) use of an asset in the solution of different problems (IEEE 1517-2010 IEEE Standard for Information Technology--System and software life cycle processes--Reuse processes, 3) (ISO/IEC/IEEE 24765j:2021)

(2) building a software system at least partly from existing pieces to perform a new application (ISO/IEC/IEEE 24765:2017 Systems and software engineering-Vocabulary)
[/FREETEXT]
