[DOCUMENT]
TITLE: embedded software

[FREETEXT]
embedded software.

(1) software that is part of a larger system and performs some of the requirements of that system (ISO/IEC/IEEE 24765:2017 Systems and software engineering-Vocabulary)

Example: software used in an aircraft or rapid transit system
[/FREETEXT]
