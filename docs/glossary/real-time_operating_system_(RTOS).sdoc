[DOCUMENT]
TITLE: real-time operating system (RTOS)

[FREETEXT]
real-time operating system (RTOS).

(1) operating system intended to handle transaction requests immediately upon receipt (ISO/IEC/IEEE 24765c:2014)
[/FREETEXT]
