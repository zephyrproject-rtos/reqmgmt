[DOCUMENT]
TITLE: operating system

[FREETEXT]
operating system.

(1) collection of software, firmware, and hardware elements that controls the execution of computer programs and provides such services as computer resource allocation, job control, input/output control, and file management in a computer system (ISO/IEC/IEEE 24765:2017 Systems and software engineering-Vocabulary)

Syn: OS
[/FREETEXT]
