[DOCUMENT]
TITLE: real-time clock (RTC)

[FREETEXT]
real-time clock (RTC).

(1) integrated circuit that tracks the current time in human units (ISO/IEC/IEEE 24765d:2015)

Syn: real time clock
[/FREETEXT]
