[DOCUMENT]
TITLE: task priority criteria

[FREETEXT]
task priority criteria.

(1) category of the task-structuring criteria addressing the relative importance of executing a given task (ISO/IEC/IEEE 24765:2017 Systems and software engineering-Vocabulary)
[/FREETEXT]
