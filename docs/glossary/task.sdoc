[DOCUMENT]
TITLE: task

[FREETEXT]
task. ... 

(2) in software design, a software component that can operate in parallel with other software components (ISO/IEC/IEEE 24765:2017 Systems and software engineering-Vocabulary) ... 
[/FREETEXT]
