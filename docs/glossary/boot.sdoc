[DOCUMENT]
TITLE: boot

[FREETEXT]
boot.

(1) to initialize a computer system by clearing memory and reloading the operating system (ISO/IEC/IEEE 24765:2017 Systems and software engineering-Vocabulary)

Note: derived from bootstrap
[/FREETEXT]
