[DOCUMENT]
TITLE: main program

[FREETEXT]
main program.

(1) software component that is called by the operating system of a computer and that usually calls other software components (ISO/IEC/IEEE 24765:2017 Systems and software engineering-Vocabulary)

See Also: routine, subprogram
[/FREETEXT]
