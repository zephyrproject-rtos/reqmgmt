[DOCUMENT]
TITLE: scheduler

[FREETEXT]
scheduler.

(1) computer program, usually part of an operating system, that schedules, initiates, and terminates jobs (ISO/IEC/IEEE 24765:2017 Systems and software engineering-Vocabulary)
[/FREETEXT]
